-- **************************************************************
--
-- Elementary Procedure definitions
--
-- **************************************************************

NBAP-PDU-Discriptions {
itu-t (0) identified-organization (4) etsi (0) mobileDomain (0) 
umts-Access (20) modules (3) nbap (2) version1 (1) nbap-PDU-Descriptions (0) }

DEFINITIONS AUTOMATIC TAGS ::= 

BEGIN

-- **************************************************************
--
-- IE parameter types from other modules.
--
-- **************************************************************

IMPORTS
	Criticality,
	ProcedureID,
	MessageDiscriminator,
	TransactionID
FROM NBAP-CommonDataTypes

	CommonTransportChannelSetupRequestFDD,
	CommonTransportChannelSetupRequestTDD,
	CommonTransportChannelSetupResponse,
	CommonTransportChannelSetupFailure,
	CommonTransportChannelReconfigurationRequestFDD,
	CommonTransportChannelReconfigurationRequestTDD,
	CommonTransportChannelReconfigurationResponse,
	CommonTransportChannelReconfigurationFailure,
	CommonTransportChannelDeletionRequest,
	CommonTransportChannelDeletionResponse,
	BlockResourceRequest,
	BlockResourceResponse,
	BlockResourceFailure,
	UnblockResourceIndication,
	AuditFailure,
	AuditRequiredIndication,
	AuditRequest,
	AuditResponse,
	CommonMeasurementInitiationRequest,
	CommonMeasurementInitiationResponse,
	CommonMeasurementInitiationFailure,
	CommonMeasurementReport,
	CommonMeasurementTerminationRequest,
	CommonMeasurementFailureIndication,
	CellSetupRequestFDD,
	CellSetupRequestTDD,
	CellSetupResponse,
	CellSetupFailure,
	CellReconfigurationRequestFDD,
	CellReconfigurationRequestTDD,
	CellReconfigurationResponse,
	CellReconfigurationFailure,
	CellDeletionRequest,
	CellDeletionResponse,
	InformationExchangeInitiationRequest,
	InformationExchangeInitiationResponse,
	InformationExchangeInitiationFailure,
	InformationReport,
	InformationExchangeTerminationRequest,
	InformationExchangeFailureIndication,
	BearerRearrangementIndication,
	ResourceStatusIndication,
	SystemInformationUpdateRequest,
	SystemInformationUpdateResponse,
	SystemInformationUpdateFailure,
	ResetRequest,
	ResetResponse,
	RadioLinkActivationCommandFDD,
	RadioLinkActivationCommandTDD,
	RadioLinkPreemptionRequiredIndication,
	RadioLinkSetupRequestFDD,
	RadioLinkSetupRequestTDD,
	RadioLinkSetupResponseFDD,
	RadioLinkSetupResponseTDD,
	RadioLinkSetupFailureFDD,
	RadioLinkSetupFailureTDD,
	RadioLinkAdditionRequestFDD,
	RadioLinkAdditionRequestTDD,
	RadioLinkAdditionResponseFDD,
	RadioLinkAdditionResponseTDD,
	RadioLinkAdditionFailureFDD,
	RadioLinkAdditionFailureTDD,
	RadioLinkParameterUpdateIndicationFDD,
	RadioLinkParameterUpdateIndicationTDD,
	RadioLinkReconfigurationPrepareFDD,
	RadioLinkReconfigurationPrepareTDD,
	RadioLinkReconfigurationReady,
	RadioLinkReconfigurationFailure,
	RadioLinkReconfigurationCommit,
	RadioLinkReconfigurationCancel,
	RadioLinkReconfigurationRequestFDD,
	RadioLinkReconfigurationRequestTDD,
	RadioLinkReconfigurationResponse,
	RadioLinkDeletionRequest,
	RadioLinkDeletionResponse,
	DL-PowerControlRequest,
	DL-PowerTimeslotControlRequest,
	DedicatedMeasurementInitiationRequest,
	DedicatedMeasurementInitiationResponse,
	DedicatedMeasurementInitiationFailure,
	DedicatedMeasurementReport,
	DedicatedMeasurementTerminationRequest,
	DedicatedMeasurementFailureIndication,
	RadioLinkFailureIndication,
	RadioLinkRestoreIndication,
	CompressedModeCommand,
	ErrorIndication,
	PrivateMessage,
	PhysicalSharedChannelReconfigurationRequestTDD,
	PhysicalSharedChannelReconfigurationRequestFDD,
	PhysicalSharedChannelReconfigurationResponse,
	PhysicalSharedChannelReconfigurationFailure,
	CellSynchronisationInitiationRequestTDD,
	CellSynchronisationInitiationResponseTDD,
	CellSynchronisationInitiationFailureTDD,
	CellSynchronisationReconfigurationRequestTDD,
	CellSynchronisationReconfigurationResponseTDD,
	CellSynchronisationReconfigurationFailureTDD,
	CellSynchronisationAdjustmentRequestTDD,
	CellSynchronisationAdjustmentResponseTDD,
	CellSynchronisationAdjustmentFailureTDD,
	CellSynchronisationReportTDD,
	CellSynchronisationTerminationRequestTDD,
	CellSynchronisationFailureIndicationTDD
FROM NBAP-PDU-Contents

	id-audit,
	id-auditRequired,
	id-blockResource,
	id-cellDeletion,
	id-cellReconfiguration,
	id-cellSetup,
	id-cellSynchronisationInitiation,
	id-cellSynchronisationReconfiguration,
	id-cellSynchronisationReporting,
	id-cellSynchronisationTermination,
	id-cellSynchronisationFailure,
	id-commonMeasurementFailure,
	id-commonMeasurementInitiation,
	id-commonMeasurementReport,
	id-commonMeasurementTermination,
	id-commonTransportChannelDelete,
	id-commonTransportChannelReconfigure,
	id-commonTransportChannelSetup,
	id-compressedModeCommand,
	id-dedicatedMeasurementFailure,
	id-dedicatedMeasurementInitiation,
	id-dedicatedMeasurementReport,
	id-dedicatedMeasurementTermination,
	id-downlinkPowerControl,
	id-downlinkPowerTimeslotControl,
	id-errorIndicationForDedicated,
	id-errorIndicationForCommon,
	id-informationExchangeFailure,
    id-informationExchangeInitiation,
    id-informationReporting,
    id-informationExchangeTermination,
	id-BearerRearrangement,
	id-physicalSharedChannelReconfiguration,
	id-privateMessageForDedicated,
	id-privateMessageForCommon,
	id-radioLinkActivation,
	id-radioLinkAddition,
	id-radioLinkDeletion,
	id-radioLinkFailure,
	id-radioLinkParameterUpdate,
	id-radioLinkPreemption,
	id-radioLinkRestoration,
	id-radioLinkSetup,
	id-reset,
	id-resourceStatusIndication,
	id-cellSynchronisationAdjustment,
	id-synchronisedRadioLinkReconfigurationCancellation,
	id-synchronisedRadioLinkReconfigurationCommit,
	id-synchronisedRadioLinkReconfigurationPreparation,
	id-systemInformationUpdate,
	id-unblockResource,
	id-unSynchronisedRadioLinkReconfiguration
FROM NBAP-Constants;

-- **************************************************************
--
-- Interface Elementary Procedure Class
--
-- **************************************************************

NBAP-ELEMENTARY-PROCEDURE ::= CLASS {
	&InitiatingMessage					,
	&SuccessfulOutcome				OPTIONAL,
	&UnsuccessfulOutcome				OPTIONAL,
	&Outcome					OPTIONAL,
	&messageDiscriminator		MessageDiscriminator	,
	&procedureID			ProcedureID 	UNIQUE	,
	&criticality			Criticality 	DEFAULT ignore
}

WITH SYNTAX {
	INITIATING MESSAGE					&InitiatingMessage
	[SUCCESSFUL OUTCOME					&SuccessfulOutcome]
	[UNSUCCESSFUL OUTCOME				&UnsuccessfulOutcome]
	[OUTCOME							&Outcome]
	MESSAGE DISCRIMINATOR				&messageDiscriminator
	PROCEDURE ID						&procedureID
	[CRITICALITY						&criticality]
}

-- **************************************************************
--
-- Interface PDU Definition
--
-- **************************************************************
NBAP-ELEMENTARY-PROCEDURES-CLASS-1 NBAP-ELEMENTARY-PROCEDURE ::= {
	cellSetupFDD										|
	cellSetupTDD										|
	cellReconfigurationFDD								|
	cellReconfigurationTDD								|
	cellDeletion										|
	commonTransportChannelSetupFDD						|
	commonTransportChannelSetupTDD						|
	commonTransportChannelReconfigureFDD				|
	commonTransportChannelReconfigureTDD				|
	commonTransportChannelDelete						|
	audit												|
	blockResource										|
	radioLinkSetupFDD									|
	radioLinkSetupTDD									|
	systemInformationUpdate								|
	commonMeasurementInitiation							|
	radioLinkAdditionFDD								|
	radioLinkAdditionTDD								|
	radioLinkDeletion									|
	reset												|
	synchronisedRadioLinkReconfigurationPreparationFDD	|
	synchronisedRadioLinkReconfigurationPreparationTDD	|
	unSynchronisedRadioLinkReconfigurationFDD			|
	unSynchronisedRadioLinkReconfigurationTDD			|
	dedicatedMeasurementInitiation						|
	physicalSharedChannelReconfigurationTDD				,
	...,
    informationExchangeInitiation						|
	cellSynchronisationInitiationTDD					|
	cellSynchronisationReconfigurationTDD				|
	cellSynchronisationAdjustmentTDD					|
	physicalSharedChannelReconfigurationFDD
}

NBAP-PDU ::= CHOICE {
	initiatingMessage		InitiatingMessage,
	succesfulOutcome		SuccessfulOutcome,
	unsuccesfulOutcome		UnsuccessfulOutcome,
	outcome					Outcome,
        ...
}

InitiatingMessage ::= SEQUENCE {
	procedureID				NBAP-ELEMENTARY-PROCEDURE.&procedureID	({NBAP-ELEMENTARY-PROCEDURES}),
	criticality				NBAP-ELEMENTARY-PROCEDURE.&criticality	({NBAP-ELEMENTARY-PROCEDURES}{@procedureID}),
	messageDiscriminator	NBAP-ELEMENTARY-PROCEDURE.&messageDiscriminator({NBAP-ELEMENTARY-PROCEDURES}{@procedureID}),
	transactionID 			TransactionID,
	value					NBAP-ELEMENTARY-PROCEDURE.&InitiatingMessage({NBAP-ELEMENTARY-PROCEDURES}{@procedureID})
}

SuccessfulOutcome ::= SEQUENCE {
	procedureID				NBAP-ELEMENTARY-PROCEDURE.&procedureID	({NBAP-ELEMENTARY-PROCEDURES}),
	criticality				NBAP-ELEMENTARY-PROCEDURE.&criticality	({NBAP-ELEMENTARY-PROCEDURES}{@procedureID}),
	messageDiscriminator	NBAP-ELEMENTARY-PROCEDURE.&messageDiscriminator({NBAP-ELEMENTARY-PROCEDURES}{@procedureID}),
 	transactionID 			TransactionID,
	value					NBAP-ELEMENTARY-PROCEDURE.&SuccessfulOutcome({NBAP-ELEMENTARY-PROCEDURES}{@procedureID})
}

UnsuccessfulOutcome ::= SEQUENCE {
	procedureID				NBAP-ELEMENTARY-PROCEDURE.&procedureID	({NBAP-ELEMENTARY-PROCEDURES}),
	criticality				NBAP-ELEMENTARY-PROCEDURE.&criticality	({NBAP-ELEMENTARY-PROCEDURES}{@procedureID}),
	messageDiscriminator	NBAP-ELEMENTARY-PROCEDURE.&messageDiscriminator({NBAP-ELEMENTARY-PROCEDURES}{@procedureID}),
	transactionID 			TransactionID,
	value					NBAP-ELEMENTARY-PROCEDURE.&UnsuccessfulOutcome({NBAP-ELEMENTARY-PROCEDURES}{@procedureID})
}

Outcome ::= SEQUENCE {
	procedureID				NBAP-ELEMENTARY-PROCEDURE.&procedureID	({NBAP-ELEMENTARY-PROCEDURES}),
	criticality				NBAP-ELEMENTARY-PROCEDURE.&criticality	({NBAP-ELEMENTARY-PROCEDURES}{@procedureID}),
	messageDiscriminator	NBAP-ELEMENTARY-PROCEDURE.&messageDiscriminator({NBAP-ELEMENTARY-PROCEDURES}{@procedureID}),
	transactionID 			TransactionID,
	value					NBAP-ELEMENTARY-PROCEDURE.&Outcome	({NBAP-ELEMENTARY-PROCEDURES}{@procedureID})
}

-- **************************************************************
--
-- Interface Elementary Procedure List
--
-- **************************************************************

NBAP-ELEMENTARY-PROCEDURES NBAP-ELEMENTARY-PROCEDURE ::= {
	NBAP-ELEMENTARY-PROCEDURES-CLASS-1			|
	NBAP-ELEMENTARY-PROCEDURES-CLASS-2			,
	...
}



NBAP-ELEMENTARY-PROCEDURES-CLASS-2 NBAP-ELEMENTARY-PROCEDURE ::= {
	resourceStatusIndication							|
	auditRequired										|
	commonMeasurementReport								|
	commonMeasurementTermination						|
	commonMeasurementFailure							|
	synchronisedRadioLinkReconfigurationCommit			|
	synchronisedRadioLinkReconfigurationCancellation	|
	radioLinkFailure									|
	radioLinkPreemption									|
	radioLinkRestoration								|
	dedicatedMeasurementReport							|
	dedicatedMeasurementTermination						|
	dedicatedMeasurementFailure							|
	downlinkPowerControlFDD								|
	downlinkPowerTimeslotControl						|
	compressedModeCommand								|
	unblockResource										|
	errorIndicationForDedicated							|
	errorIndicationForCommon							|
	privateMessageForDedicated							|
	privateMessageForCommon								,
	...,
	informationReporting								|
	informationExchangeTermination						|
	informationExchangeFailure							|
	cellSynchronisationReportingTDD						|
	cellSynchronisationTerminationTDD					|
	cellSynchronisationFailureTDD						|
	bearerRearrangement									|
	radioLinkActivationFDD								|
	radioLinkActivationTDD								|
	radioLinkParameterUpdateFDD							|
	radioLinkParameterUpdateTDD
}

-- **************************************************************
--
-- Interface Elementary Procedures
--
-- **************************************************************

-- Class 1

-- *** CellSetup (FDD) ***
cellSetupFDD NBAP-ELEMENTARY-PROCEDURE ::= {
	INITIATING MESSAGE		CellSetupRequestFDD
	SUCCESSFUL OUTCOME		CellSetupResponse
	UNSUCCESSFUL OUTCOME	CellSetupFailure
	MESSAGE DISCRIMINATOR	common
	PROCEDURE ID 			{ procedureCode id-cellSetup, ddMode fdd } 
	CRITICALITY 			reject
}

-- *** CellSetup (TDD) ***
cellSetupTDD NBAP-ELEMENTARY-PROCEDURE ::= {
	INITIATING MESSAGE		CellSetupRequestTDD
	SUCCESSFUL OUTCOME		CellSetupResponse
	UNSUCCESSFUL OUTCOME	CellSetupFailure
	MESSAGE DISCRIMINATOR	common
	PROCEDURE ID 			{ procedureCode id-cellSetup, ddMode tdd } 
	CRITICALITY 			reject
}

-- *** CellReconfiguration(FDD) ***
cellReconfigurationFDD NBAP-ELEMENTARY-PROCEDURE ::= {
	INITIATING MESSAGE		CellReconfigurationRequestFDD
	SUCCESSFUL OUTCOME		CellReconfigurationResponse
	UNSUCCESSFUL OUTCOME	CellReconfigurationFailure
	MESSAGE DISCRIMINATOR	common
	PROCEDURE ID 			{ procedureCode id-cellReconfiguration, ddMode fdd } 
	CRITICALITY 			reject
}

-- *** CellReconfiguration(TDD) ***
cellReconfigurationTDD NBAP-ELEMENTARY-PROCEDURE ::= {
	INITIATING MESSAGE		CellReconfigurationRequestTDD
	SUCCESSFUL OUTCOME		CellReconfigurationResponse
	UNSUCCESSFUL OUTCOME	CellReconfigurationFailure
	MESSAGE DISCRIMINATOR	common
	PROCEDURE ID 			{ procedureCode id-cellReconfiguration,	ddMode tdd } 
	CRITICALITY 			reject
}

-- *** CellDeletion ***
cellDeletion NBAP-ELEMENTARY-PROCEDURE ::= {
	INITIATING MESSAGE		CellDeletionRequest
	SUCCESSFUL OUTCOME		CellDeletionResponse
	MESSAGE DISCRIMINATOR	common
	PROCEDURE ID 			{ procedureCode id-cellDeletion, ddMode common } 
	CRITICALITY 			reject
}

-- *** CommonTransportChannelSetup (FDD) ***
commonTransportChannelSetupFDD NBAP-ELEMENTARY-PROCEDURE ::= {
	INITIATING MESSAGE		CommonTransportChannelSetupRequestFDD
	SUCCESSFUL OUTCOME		CommonTransportChannelSetupResponse
	UNSUCCESSFUL OUTCOME	CommonTransportChannelSetupFailure
	MESSAGE DISCRIMINATOR	common
	PROCEDURE ID 			{ procedureCode id-commonTransportChannelSetup, ddMode fdd } 
	CRITICALITY 			reject
}

-- *** CommonTransportChannelSetup (TDD) ***
commonTransportChannelSetupTDD NBAP-ELEMENTARY-PROCEDURE ::= {
	INITIATING MESSAGE		CommonTransportChannelSetupRequestTDD
	SUCCESSFUL OUTCOME		CommonTransportChannelSetupResponse
	UNSUCCESSFUL OUTCOME	CommonTransportChannelSetupFailure
	MESSAGE DISCRIMINATOR	common
	PROCEDURE ID 			{ procedureCode id-commonTransportChannelSetup, ddMode tdd } 
	CRITICALITY 			reject
}

-- *** CommonTransportChannelReconfigure (FDD) ***
commonTransportChannelReconfigureFDD NBAP-ELEMENTARY-PROCEDURE ::= {
	INITIATING MESSAGE		CommonTransportChannelReconfigurationRequestFDD
	SUCCESSFUL OUTCOME		CommonTransportChannelReconfigurationResponse
	UNSUCCESSFUL OUTCOME	CommonTransportChannelReconfigurationFailure
	MESSAGE DISCRIMINATOR	common
	PROCEDURE ID 			{ procedureCode id-commonTransportChannelReconfigure, ddMode fdd } 
	CRITICALITY 			reject
}

-- *** CommonTransportChannelReconfigure (TDD) ***
commonTransportChannelReconfigureTDD NBAP-ELEMENTARY-PROCEDURE ::= {
	INITIATING MESSAGE		CommonTransportChannelReconfigurationRequestTDD
	SUCCESSFUL OUTCOME		CommonTransportChannelReconfigurationResponse
	UNSUCCESSFUL OUTCOME	CommonTransportChannelReconfigurationFailure
	MESSAGE DISCRIMINATOR	common
	PROCEDURE ID 			{ procedureCode id-commonTransportChannelReconfigure, ddMode tdd } 
	CRITICALITY 			reject
}

-- *** CommonTransportChannelDelete ***
commonTransportChannelDelete NBAP-ELEMENTARY-PROCEDURE ::= {
	INITIATING MESSAGE		CommonTransportChannelDeletionRequest
	SUCCESSFUL OUTCOME		CommonTransportChannelDeletionResponse
	MESSAGE DISCRIMINATOR	common
	PROCEDURE ID 			{ procedureCode id-commonTransportChannelDelete, ddMode common } 
	CRITICALITY 			reject
}

-- *** Audit ***
audit NBAP-ELEMENTARY-PROCEDURE ::= {
	INITIATING MESSAGE		AuditRequest
	SUCCESSFUL OUTCOME		AuditResponse
	UNSUCCESSFUL OUTCOME	AuditFailure
	MESSAGE DISCRIMINATOR	common
	PROCEDURE ID 			{ procedureCode id-audit, ddMode common } 
	CRITICALITY 			reject
}

-- *** BlockResourceRequest ***
blockResource NBAP-ELEMENTARY-PROCEDURE ::= {
	INITIATING MESSAGE		BlockResourceRequest
	SUCCESSFUL OUTCOME		BlockResourceResponse
	UNSUCCESSFUL OUTCOME	BlockResourceFailure
	MESSAGE DISCRIMINATOR	common
	PROCEDURE ID 			{ procedureCode id-blockResource, ddMode common } 
	CRITICALITY 			reject
}

-- *** RadioLinkSetup (FDD) ***
radioLinkSetupFDD NBAP-ELEMENTARY-PROCEDURE ::= {
	INITIATING MESSAGE		RadioLinkSetupRequestFDD
	SUCCESSFUL OUTCOME		RadioLinkSetupResponseFDD
	UNSUCCESSFUL OUTCOME	RadioLinkSetupFailureFDD
	MESSAGE DISCRIMINATOR	common
	PROCEDURE ID 			{ procedureCode id-radioLinkSetup, ddMode fdd } 
	CRITICALITY 			reject
}

-- *** RadioLinkSetup (TDD) ***
radioLinkSetupTDD NBAP-ELEMENTARY-PROCEDURE ::= {
	INITIATING MESSAGE		RadioLinkSetupRequestTDD
	SUCCESSFUL OUTCOME		RadioLinkSetupResponseTDD
	UNSUCCESSFUL OUTCOME	RadioLinkSetupFailureTDD
	MESSAGE DISCRIMINATOR	common
	PROCEDURE ID 			{ procedureCode id-radioLinkSetup, ddMode tdd } 
	CRITICALITY 			reject
}

-- *** SystemInformationUpdate ***
systemInformationUpdate NBAP-ELEMENTARY-PROCEDURE ::= {
	INITIATING MESSAGE		SystemInformationUpdateRequest
	SUCCESSFUL OUTCOME		SystemInformationUpdateResponse
	UNSUCCESSFUL OUTCOME	SystemInformationUpdateFailure
	MESSAGE DISCRIMINATOR	common
	PROCEDURE ID 			{ procedureCode id-systemInformationUpdate, ddMode common } 
	CRITICALITY 			reject
}

-- *** Reset ***
reset NBAP-ELEMENTARY-PROCEDURE ::= {
	INITIATING MESSAGE		ResetRequest
	SUCCESSFUL OUTCOME		ResetResponse
	MESSAGE DISCRIMINATOR	common
	PROCEDURE ID 			{ procedureCode id-reset, ddMode common } 
	CRITICALITY 			reject
}

-- *** CommonMeasurementInitiation ***
commonMeasurementInitiation NBAP-ELEMENTARY-PROCEDURE ::= {
	INITIATING MESSAGE		CommonMeasurementInitiationRequest
	SUCCESSFUL OUTCOME		CommonMeasurementInitiationResponse
	UNSUCCESSFUL OUTCOME	CommonMeasurementInitiationFailure
	MESSAGE DISCRIMINATOR	common
	PROCEDURE ID 			{ procedureCode id-commonMeasurementInitiation,	ddMode common } 
	CRITICALITY 			reject
}

-- *** RadioLinkAddition (FDD) ***
radioLinkAdditionFDD NBAP-ELEMENTARY-PROCEDURE ::= {
	INITIATING MESSAGE		RadioLinkAdditionRequestFDD
	SUCCESSFUL OUTCOME		RadioLinkAdditionResponseFDD
	UNSUCCESSFUL OUTCOME	RadioLinkAdditionFailureFDD
	MESSAGE DISCRIMINATOR	dedicated
	PROCEDURE ID 			{ procedureCode id-radioLinkAddition, ddMode fdd } 
	CRITICALITY 			reject
}

-- *** RadioLinkAddition (TDD) ***
radioLinkAdditionTDD NBAP-ELEMENTARY-PROCEDURE ::= {
	INITIATING MESSAGE		RadioLinkAdditionRequestTDD
	SUCCESSFUL OUTCOME		RadioLinkAdditionResponseTDD
	UNSUCCESSFUL OUTCOME	RadioLinkAdditionFailureTDD
	MESSAGE DISCRIMINATOR	dedicated
	PROCEDURE ID 			{ procedureCode id-radioLinkAddition, ddMode tdd } 
	CRITICALITY 			reject
}

-- *** RadioLinkDeletion	***
radioLinkDeletion NBAP-ELEMENTARY-PROCEDURE ::= {
	INITIATING MESSAGE		RadioLinkDeletionRequest
	SUCCESSFUL OUTCOME		RadioLinkDeletionResponse
	MESSAGE DISCRIMINATOR	dedicated
	PROCEDURE ID 			{ procedureCode id-radioLinkDeletion, ddMode common }
	CRITICALITY 			reject
}

-- *** SynchronisedRadioLinkReconfigurationPreparation (FDD) ***
synchronisedRadioLinkReconfigurationPreparationFDD NBAP-ELEMENTARY-PROCEDURE ::= {
	INITIATING MESSAGE		RadioLinkReconfigurationPrepareFDD
	SUCCESSFUL OUTCOME		RadioLinkReconfigurationReady
	UNSUCCESSFUL OUTCOME	RadioLinkReconfigurationFailure
	MESSAGE DISCRIMINATOR	dedicated
	PROCEDURE ID 			{ procedureCode id-synchronisedRadioLinkReconfigurationPreparation, ddMode fdd } 
	CRITICALITY 			reject
}

-- *** SynchronisedRadioLinkReconfigurationPreparation (TDD) ***
synchronisedRadioLinkReconfigurationPreparationTDD NBAP-ELEMENTARY-PROCEDURE ::= {
	INITIATING MESSAGE		RadioLinkReconfigurationPrepareTDD
	SUCCESSFUL OUTCOME		RadioLinkReconfigurationReady
	UNSUCCESSFUL OUTCOME	RadioLinkReconfigurationFailure
	MESSAGE DISCRIMINATOR	dedicated
	PROCEDURE ID 			{ procedureCode id-synchronisedRadioLinkReconfigurationPreparation, ddMode tdd } 
	CRITICALITY 			reject
}

-- *** UnSynchronisedRadioLinkReconfiguration (FDD) ***
unSynchronisedRadioLinkReconfigurationFDD NBAP-ELEMENTARY-PROCEDURE ::= {
	INITIATING MESSAGE		RadioLinkReconfigurationRequestFDD
	SUCCESSFUL OUTCOME		RadioLinkReconfigurationResponse
	UNSUCCESSFUL OUTCOME	RadioLinkReconfigurationFailure
	MESSAGE DISCRIMINATOR	dedicated
	PROCEDURE ID 			{ procedureCode id-unSynchronisedRadioLinkReconfiguration, ddMode fdd } 
	CRITICALITY 			reject
}

-- *** UnSynchronisedRadioLinkReconfiguration (TDD) ***
unSynchronisedRadioLinkReconfigurationTDD NBAP-ELEMENTARY-PROCEDURE ::= {
	INITIATING MESSAGE		RadioLinkReconfigurationRequestTDD
	SUCCESSFUL OUTCOME		RadioLinkReconfigurationResponse
	UNSUCCESSFUL OUTCOME	RadioLinkReconfigurationFailure
	MESSAGE DISCRIMINATOR	dedicated
	PROCEDURE ID 			{ procedureCode id-unSynchronisedRadioLinkReconfiguration, ddMode tdd } 
	CRITICALITY 			reject
}

-- *** DedicatedMeasurementInitiation  ***
dedicatedMeasurementInitiation NBAP-ELEMENTARY-PROCEDURE ::= {
	INITIATING MESSAGE		DedicatedMeasurementInitiationRequest
	SUCCESSFUL OUTCOME		DedicatedMeasurementInitiationResponse
	UNSUCCESSFUL OUTCOME	DedicatedMeasurementInitiationFailure
	MESSAGE DISCRIMINATOR	dedicated
	PROCEDURE ID 			{ procedureCode id-dedicatedMeasurementInitiation, ddMode common }
	CRITICALITY 			reject
}

-- *** PhysicalSharedChannelReconfiguration (FDD) ***
physicalSharedChannelReconfigurationFDD NBAP-ELEMENTARY-PROCEDURE ::= {
	INITIATING MESSAGE	PhysicalSharedChannelReconfigurationRequestFDD
	SUCCESSFUL OUTCOME	PhysicalSharedChannelReconfigurationResponse
	UNSUCCESSFUL OUTCOME	PhysicalSharedChannelReconfigurationFailure
	MESSAGE DISCRIMINATOR	common
	PROCEDURE ID 		{ procedureCode id-physicalSharedChannelReconfiguration, ddMode fdd } 
	CRITICALITY 		reject
}

-- *** PhysicalSharedChannelReconfiguration (TDD) ***
physicalSharedChannelReconfigurationTDD NBAP-ELEMENTARY-PROCEDURE ::= {
	INITIATING MESSAGE	PhysicalSharedChannelReconfigurationRequestTDD
	SUCCESSFUL OUTCOME	PhysicalSharedChannelReconfigurationResponse
	UNSUCCESSFUL OUTCOME	PhysicalSharedChannelReconfigurationFailure
	MESSAGE DISCRIMINATOR	common
	PROCEDURE ID 		{ procedureCode id-physicalSharedChannelReconfiguration, ddMode tdd } 
	CRITICALITY 		reject
}

--*** InformationExchangeInitiation ***
informationExchangeInitiation NBAP-ELEMENTARY-PROCEDURE ::= {
    INITIATING MESSAGE		InformationExchangeInitiationRequest
	SUCCESSFUL OUTCOME		InformationExchangeInitiationResponse
	UNSUCCESSFUL OUTCOME	InformationExchangeInitiationFailure
	MESSAGE DISCRIMINATOR	common
	PROCEDURE ID 			{ procedureCode id-informationExchangeInitiation,	ddMode common } 
	CRITICALITY 			reject
}

-- *** CellSynchronisationInitiation (TDD only) ***
cellSynchronisationInitiationTDD NBAP-ELEMENTARY-PROCEDURE ::= {
	INITIATING MESSAGE	CellSynchronisationInitiationRequestTDD
	SUCCESSFUL OUTCOME	CellSynchronisationInitiationResponseTDD
	UNSUCCESSFUL OUTCOME	CellSynchronisationInitiationFailureTDD
	MESSAGE DISCRIMINATOR	common
	PROCEDURE ID 		{ procedureCode id-cellSynchronisationInitiation, ddMode tdd } 
	CRITICALITY 		reject
}

-- *** CellSynchronisationReconfiguration (TDD only) ***
cellSynchronisationReconfigurationTDD NBAP-ELEMENTARY-PROCEDURE ::= {
	INITIATING MESSAGE	CellSynchronisationReconfigurationRequestTDD
	SUCCESSFUL OUTCOME	CellSynchronisationReconfigurationResponseTDD
	UNSUCCESSFUL OUTCOME	CellSynchronisationReconfigurationFailureTDD
	MESSAGE DISCRIMINATOR	common
	PROCEDURE ID 		{ procedureCode id-cellSynchronisationReconfiguration, ddMode tdd } 
	CRITICALITY 		reject
}

-- *** CellSynchronisationAdjustment (TDD only) ***
cellSynchronisationAdjustmentTDD NBAP-ELEMENTARY-PROCEDURE ::= {
	INITIATING MESSAGE	CellSynchronisationAdjustmentRequestTDD
	SUCCESSFUL OUTCOME	CellSynchronisationAdjustmentResponseTDD
	UNSUCCESSFUL OUTCOME	CellSynchronisationAdjustmentFailureTDD
	MESSAGE DISCRIMINATOR	common
	PROCEDURE ID 		{ procedureCode id-cellSynchronisationAdjustment, ddMode tdd } 
	CRITICALITY 		reject
}

-- Class 2

-- *** ResourceStatusIndication ***
resourceStatusIndication NBAP-ELEMENTARY-PROCEDURE ::= {
	INITIATING MESSAGE		ResourceStatusIndication
	MESSAGE DISCRIMINATOR	common
	PROCEDURE ID 			{ procedureCode id-resourceStatusIndication, ddMode common } 
	CRITICALITY 			ignore
}

-- *** AuditRequired ***
auditRequired NBAP-ELEMENTARY-PROCEDURE ::= {
	INITIATING MESSAGE		AuditRequiredIndication
	MESSAGE DISCRIMINATOR	common
	PROCEDURE ID 			{ procedureCode id-auditRequired, ddMode common } 
	CRITICALITY 			ignore
}

-- *** CommonMeasurementReport ***
commonMeasurementReport NBAP-ELEMENTARY-PROCEDURE ::= {
	INITIATING MESSAGE		CommonMeasurementReport
	MESSAGE DISCRIMINATOR	common
	PROCEDURE ID 			{ procedureCode id-commonMeasurementReport, ddMode common } 
	CRITICALITY 			ignore
}

-- *** CommonMeasurementTermination ***
commonMeasurementTermination NBAP-ELEMENTARY-PROCEDURE ::= {
	INITIATING MESSAGE		CommonMeasurementTerminationRequest
	MESSAGE DISCRIMINATOR	common
	PROCEDURE ID 			{ procedureCode id-commonMeasurementTermination, ddMode common } 
	CRITICALITY 			ignore
}

-- *** CommonMeasurementFailure ***
commonMeasurementFailure NBAP-ELEMENTARY-PROCEDURE ::= {
	INITIATING MESSAGE		CommonMeasurementFailureIndication
	MESSAGE DISCRIMINATOR	common
	PROCEDURE ID 			{ procedureCode id-commonMeasurementFailure, ddMode common } 
	CRITICALITY 			ignore
}

-- *** SynchronisedRadioLinkReconfirurationCommit ***
synchronisedRadioLinkReconfigurationCommit NBAP-ELEMENTARY-PROCEDURE ::= {
	INITIATING MESSAGE		RadioLinkReconfigurationCommit
	MESSAGE DISCRIMINATOR	dedicated
	PROCEDURE ID 			{ procedureCode id-synchronisedRadioLinkReconfigurationCommit, ddMode common } 
	CRITICALITY 			ignore
}

-- *** SynchronisedRadioReconfigurationCancellation ***
synchronisedRadioLinkReconfigurationCancellation NBAP-ELEMENTARY-PROCEDURE ::= {
	INITIATING MESSAGE		RadioLinkReconfigurationCancel
	MESSAGE DISCRIMINATOR	dedicated
	PROCEDURE ID 			{ procedureCode id-synchronisedRadioLinkReconfigurationCancellation, ddMode common } 
	CRITICALITY 			ignore
}

-- *** RadioLinkFailure ***
radioLinkFailure NBAP-ELEMENTARY-PROCEDURE ::= {
	INITIATING MESSAGE		RadioLinkFailureIndication
	MESSAGE DISCRIMINATOR	dedicated
	PROCEDURE ID 			{ procedureCode id-radioLinkFailure, ddMode common }
	CRITICALITY 			ignore
}

-- *** RadioLinkPreemption ***
radioLinkPreemption NBAP-ELEMENTARY-PROCEDURE ::= {
	INITIATING MESSAGE	RadioLinkPreemptionRequiredIndication
	MESSAGE DISCRIMINATOR	dedicated
	PROCEDURE ID		{ procedureCode id-radioLinkPreemption, ddMode common }
	CRITICALITY		ignore
}

-- *** RadioLinkRestoration ***
radioLinkRestoration NBAP-ELEMENTARY-PROCEDURE ::= {
	INITIATING MESSAGE		RadioLinkRestoreIndication
	MESSAGE DISCRIMINATOR	dedicated
	PROCEDURE ID 			{ procedureCode id-radioLinkRestoration, ddMode common }
	CRITICALITY 			ignore
}

-- *** DedicatedMeasurementReport ***
dedicatedMeasurementReport NBAP-ELEMENTARY-PROCEDURE ::= {
	INITIATING MESSAGE		DedicatedMeasurementReport
	MESSAGE DISCRIMINATOR	dedicated
	PROCEDURE ID 			{ procedureCode id-dedicatedMeasurementReport, ddMode common }
	CRITICALITY 			ignore
}

-- *** DedicatedMeasurementTermination  ***
dedicatedMeasurementTermination NBAP-ELEMENTARY-PROCEDURE ::= {
	INITIATING MESSAGE		DedicatedMeasurementTerminationRequest
	MESSAGE DISCRIMINATOR	dedicated
	PROCEDURE ID 			{ procedureCode id-dedicatedMeasurementTermination, ddMode common }
	CRITICALITY 			ignore
}

-- *** DedicatedMeasurementFailure ***
dedicatedMeasurementFailure NBAP-ELEMENTARY-PROCEDURE ::= {
	INITIATING MESSAGE		DedicatedMeasurementFailureIndication
	MESSAGE DISCRIMINATOR	dedicated
	PROCEDURE ID 			{ procedureCode id-dedicatedMeasurementFailure, ddMode common }
	CRITICALITY 			ignore
}

-- *** DLPowerControl (FDD only) ***
downlinkPowerControlFDD NBAP-ELEMENTARY-PROCEDURE ::= {
	INITIATING MESSAGE		DL-PowerControlRequest
	MESSAGE DISCRIMINATOR	dedicated
	PROCEDURE ID 			{ procedureCode id-downlinkPowerControl, ddMode fdd }
	CRITICALITY 			ignore
}

-- *** DLPowerTimeslotControl (TDD only) ***
downlinkPowerTimeslotControl NBAP-ELEMENTARY-PROCEDURE ::= {
	INITIATING MESSAGE		DL-PowerTimeslotControlRequest
	MESSAGE DISCRIMINATOR	dedicated
	PROCEDURE ID 			{ procedureCode id-downlinkPowerTimeslotControl, ddMode tdd }
	CRITICALITY 			ignore
}

-- *** CompressedModeCommand (FDD only) ***
compressedModeCommand NBAP-ELEMENTARY-PROCEDURE ::= {
	INITIATING MESSAGE		CompressedModeCommand
	MESSAGE DISCRIMINATOR	dedicated
	PROCEDURE ID 			{ procedureCode id-compressedModeCommand, ddMode fdd }
	CRITICALITY 			ignore
}

-- *** UnblockResourceIndication ***
unblockResource NBAP-ELEMENTARY-PROCEDURE ::= {
	INITIATING MESSAGE		UnblockResourceIndication
	MESSAGE DISCRIMINATOR	common
	PROCEDURE ID 			{ procedureCode id-unblockResource, ddMode common } 
	CRITICALITY 			ignore
}

-- *** ErrorIndication for Dedicated procedures ***
errorIndicationForDedicated NBAP-ELEMENTARY-PROCEDURE ::= {
	INITIATING MESSAGE		ErrorIndication
	MESSAGE DISCRIMINATOR	dedicated
	PROCEDURE ID 			{ procedureCode	id-errorIndicationForDedicated, ddMode common }
	CRITICALITY 			ignore
}

-- *** ErrorIndication for Common procedures ***
errorIndicationForCommon NBAP-ELEMENTARY-PROCEDURE ::= {
	INITIATING MESSAGE		ErrorIndication
	MESSAGE DISCRIMINATOR	common
	PROCEDURE ID 			{ procedureCode	id-errorIndicationForCommon, ddMode common }
	CRITICALITY 			ignore
}

-- *** CellSynchronisationReporting (TDD only) ***
cellSynchronisationReportingTDD NBAP-ELEMENTARY-PROCEDURE ::= {
	INITIATING MESSAGE		CellSynchronisationReportTDD
	MESSAGE DISCRIMINATOR	common
	PROCEDURE ID 			{ procedureCode	id-cellSynchronisationReporting, ddMode tdd }
	CRITICALITY 			ignore
}

-- *** CellSynchronisationTermination (TDD only) ***
cellSynchronisationTerminationTDD NBAP-ELEMENTARY-PROCEDURE ::= {
	INITIATING MESSAGE		CellSynchronisationTerminationRequestTDD
	MESSAGE DISCRIMINATOR	common
	PROCEDURE ID 			{ procedureCode	id-cellSynchronisationTermination, ddMode tdd }
	CRITICALITY 			ignore
}

-- *** CellSynchronisationFailure (TDD only) ***
cellSynchronisationFailureTDD NBAP-ELEMENTARY-PROCEDURE ::= {
	INITIATING MESSAGE		CellSynchronisationFailureIndicationTDD
	MESSAGE DISCRIMINATOR	common
	PROCEDURE ID 			{ procedureCode	id-cellSynchronisationFailure, ddMode tdd }
	CRITICALITY 			ignore
}

-- *** PrivateMessage for Dedicated procedures ***
privateMessageForDedicated NBAP-ELEMENTARY-PROCEDURE ::= {
	INITIATING MESSAGE		PrivateMessage
	MESSAGE DISCRIMINATOR	dedicated
	PROCEDURE ID			{ procedureCode	id-privateMessageForDedicated, ddMode common }
	CRITICALITY				ignore
}

-- *** PrivateMessage for Common procedures ***
privateMessageForCommon NBAP-ELEMENTARY-PROCEDURE ::= {
	INITIATING MESSAGE		PrivateMessage
	MESSAGE DISCRIMINATOR	common
	PROCEDURE ID			{ procedureCode	id-privateMessageForCommon, ddMode common }
	CRITICALITY				ignore
}

-- *** InformationReporting ***
informationReporting NBAP-ELEMENTARY-PROCEDURE ::= {
	INITIATING MESSAGE		InformationReport
	MESSAGE DISCRIMINATOR	common
	PROCEDURE ID 			{ procedureCode id-informationReporting, ddMode common } 
	CRITICALITY 			ignore
}

-- *** InformationExchangeTermination ***
informationExchangeTermination NBAP-ELEMENTARY-PROCEDURE ::= {
	INITIATING MESSAGE		InformationExchangeTerminationRequest
	MESSAGE DISCRIMINATOR	common
	PROCEDURE ID 			{ procedureCode id-informationExchangeTermination, ddMode common } 
	CRITICALITY 			ignore
}

-- *** InformationExchangeFailure ***
informationExchangeFailure NBAP-ELEMENTARY-PROCEDURE ::= {
	INITIATING MESSAGE		InformationExchangeFailureIndication
	MESSAGE DISCRIMINATOR	common
	PROCEDURE ID 			{ procedureCode id-informationExchangeFailure, ddMode common } 
	CRITICALITY 			ignore
}

-- *** BearerRearrangement ***
bearerRearrangement NBAP-ELEMENTARY-PROCEDURE ::= {
	INITIATING MESSAGE		BearerRearrangementIndication
	MESSAGE DISCRIMINATOR	dedicated
	PROCEDURE ID 			{ procedureCode id-BearerRearrangement, ddMode common }
	CRITICALITY 			ignore
}

-- *** RadioLinkActivation (FDD) ***
radioLinkActivationFDD NBAP-ELEMENTARY-PROCEDURE ::= {
	INITIATING MESSAGE		RadioLinkActivationCommandFDD
	MESSAGE DISCRIMINATOR	dedicated
	PROCEDURE ID			{ procedureCode id-radioLinkActivation, ddMode fdd }
	CRITICALITY				ignore
}

-- *** RadioLinkActivation (TDD) ***
radioLinkActivationTDD NBAP-ELEMENTARY-PROCEDURE ::= {
	INITIATING MESSAGE		RadioLinkActivationCommandTDD
	MESSAGE DISCRIMINATOR	dedicated
	PROCEDURE ID			{ procedureCode id-radioLinkActivation, ddMode tdd }
	CRITICALITY				ignore
}

-- *** RadioLinkParameterUpdate (FDD) ***
radioLinkParameterUpdateFDD NBAP-ELEMENTARY-PROCEDURE ::= {
	INITIATING MESSAGE		RadioLinkParameterUpdateIndicationFDD
	MESSAGE DISCRIMINATOR	dedicated
	PROCEDURE ID 			{ procedureCode id-radioLinkParameterUpdate, ddMode fdd }
	CRITICALITY 			ignore
}

-- *** RadioLinkParameterUpdate (TDD) ***
radioLinkParameterUpdateTDD NBAP-ELEMENTARY-PROCEDURE ::= {
	INITIATING MESSAGE		RadioLinkParameterUpdateIndicationTDD
	MESSAGE DISCRIMINATOR	dedicated
	PROCEDURE ID 			{ procedureCode id-radioLinkParameterUpdate, ddMode tdd }
	CRITICALITY 			ignore
}

END
	
-- **************************************************************
--
-- PDU definitions for NBAP.
--
-- **************************************************************

NBAP-PDU-Contents {
itu-t (0) identified-organization (4) etsi (0) mobileDomain (0) 
umts-Access (20) modules (3) nbap (2) version1 (1) nbap-PDU-Contents (1) }

DEFINITIONS AUTOMATIC TAGS ::= 

BEGIN

-- **************************************************************
--
-- IE parameter types from other modules.
--
-- **************************************************************

IMPORTS
	Active-Pattern-Sequence-Information,
	AddorDeleteIndicator,
	AICH-Power,
	AICH-TransmissionTiming,
	AllocationRetentionPriority,
	APPreambleSignature,
	APSubChannelNumber,
	AvailabilityStatus,
	BCCH-ModificationTime,
	BindingID,
	BlockingPriorityIndicator,
	SCTD-Indicator,
	Cause,
	CCTrCH-ID,
	CDSubChannelNumbers,
	CellParameterID,
	CellSyncBurstCode,
	CellSyncBurstCodeShift,
	CellSyncBurstRepetitionPeriod,
	CellSyncBurstSIR,
	CellSyncBurstTiming,
	CellSyncBurstTimingThreshold,
	CFN,
	Channel-Assignment-Indication,
	ChipOffset,
	C-ID,
	Closedlooptimingadjustmentmode,
	CommonChannelsCapacityConsumptionLaw,
	Compressed-Mode-Deactivation-Flag,
	CommonMeasurementAccuracy,
	CommonMeasurementType,
	CommonMeasurementValue,
	CommonMeasurementValueInformation,
	CommonPhysicalChannelID,
	Common-PhysicalChannel-Status-Information,
	Common-TransportChannel-Status-Information,
	CommonTransportChannelID,
	CommonTransportChannel-InformationResponse,
	CommunicationControlPortID,
	ConfigurationGenerationID,
	ConstantValue,
	CriticalityDiagnostics,
	CPCH-Allowed-Total-Rate,
	CPCHScramblingCodeNumber,
	CPCH-UL-DPCCH-SlotFormat,
	CRNC-CommunicationContextID,
	CSBMeasurementID,
	CSBTransmissionID,
	DCH-FDD-Information,
	DCH-InformationResponse,
	DCH-ID,
	FDD-DCHs-to-Modify,
	TDD-DCHs-to-Modify,
	DCH-TDD-Information,
	DedicatedChannelsCapacityConsumptionLaw,
	DedicatedMeasurementType,
	DedicatedMeasurementValue,
	DedicatedMeasurementValueInformation,
	DelayedActivation,
	DelayedActivationUpdate,
	DiversityControlField,
	DiversityMode,
	DL-DPCH-SlotFormat,
	DL-DPCH-TimingAdjustment,
	DL-or-Global-CapacityCredit,
	DL-Power,
	DL-PowerBalancing-Information,
	DL-PowerBalancing-ActivationIndicator,
	DLPowerAveragingWindowSize,
	DL-PowerBalancing-UpdatedIndicator,
	DL-ScramblingCode,
	DL-TimeslotISCP,
	DL-Timeslot-Information,
	DL-TimeslotLCR-Information,
	DL-TimeslotISCPInfo,
	DL-TimeslotISCPInfoLCR,
	DL-TPC-Pattern01Count,
	DPC-Mode,
	DPCH-ID,
	DSCH-ID,
	DSCH-FDD-Common-Information,
	DSCH-FDD-Information,
	DSCH-InformationResponse,
	DSCH-TDD-Information,
	DwPCH-Power,
	End-Of-Audit-Sequence-Indicator,
	EnhancedDSCHPC,
	EnhancedDSCHPCCounter,
	EnhancedDSCHPCIndicator,
	EnhancedDSCHPCWnd,
	EnhancedDSCHPowerOffset,
	FDD-DL-ChannelisationCodeNumber,
	FDD-DL-CodeInformation,
	FDD-S-CCPCH-Offset,
	FDD-TPC-DownlinkStepSize,
	FirstRLS-Indicator,
    FNReportingIndicator,
	FPACH-Power,
	FrameAdjustmentValue,
	FrameHandlingPriority,
	FrameOffset,
	HS-PDSCH-FDD-Code-Information,
	HS-SCCH-ID,
	HS-SCCH-FDD-Code-Information,
	IB-OC-ID,
	IB-SG-DATA,
	IB-SG-POS,
	IB-SG-REP,
	IB-Type,
	InformationExchangeID,
    InformationReportCharacteristics,
    InformationType,
	InnerLoopDLPCStatus,
	IPDL-FDD-Parameters,
	IPDL-TDD-Parameters,
	IPDL-Indicator,
	IPDL-TDD-Parameters-LCR,
	LimitedPowerIncrease,
	Local-Cell-ID,
	MaximumDL-PowerCapability,
	Maximum-PDSCH-Power,
	MaximumTransmissionPower,
	Max-Number-of-PCPCHes,
	MaxNrOfUL-DPDCHs,
	MaxPRACH-MidambleShifts,
	MeasurementFilterCoefficient,
	MeasurementID,
	MidambleAllocationMode,
	MidambleShiftAndBurstType,
	MidambleShiftLCR,
	MinimumDL-PowerCapability,
	MinSpreadingFactor,
	MinUL-ChannelisationCodeLength,
	MultiplexingPosition,
	NEOT,
	NCyclesPerSFNperiod,
	NFmax,
	NRepetitionsPerCyclePeriod,
	N-INSYNC-IND,
 	N-OUTSYNC-IND,
	NeighbouringCellMeasurementInformation,
	NeighbouringFDDCellMeasurementInformation,
	NeighbouringTDDCellMeasurementInformation,
	NodeB-CommunicationContextID,
	NStartMessage,
	NSubCyclesPerCyclePeriod,
	PagingIndicatorLength,
	PayloadCRC-PresenceIndicator,
	PCCPCH-Power,
	PCP-Length,
	PDSCH-CodeMapping,
	PDSCHSet-ID,
	PDSCH-ID,
	PICH-Mode,
	PICH-Power,
	PowerAdjustmentType,
	PowerOffset,
	PowerRaiseLimit,
	PRACH-Midamble,
	PreambleSignatures,
	PreambleThreshold,
	PredictedSFNSFNDeviationLimit,
	PredictedTUTRANGPSDeviationLimit,
	PrimaryCPICH-Power,
	PrimaryScramblingCode,
	PropagationDelay,
	SCH-TimeSlot,
	PunctureLimit,
	PUSCHSet-ID,
	PUSCH-ID,
	QE-Selector,
	Qth-Parameter,
	RACH-SlotFormat,
	RACH-SubChannelNumbers,
	ReferenceClockAvailability,
	ReferenceSFNoffset,
	RepetitionLength,
	RepetitionPeriod,
	ReportCharacteristics,
	RequestedDataValue,
    RequestedDataValueInformation,
	ResourceOperationalState,
	RL-Set-ID,
	RL-ID,
	RL-Specific-DCH-Info,
	Received-total-wide-band-power-Value,
	AdjustmentPeriod,
	ScaledAdjustmentRatio,
	MaxAdjustmentStep,
	RNC-ID,
	ScramblingCodeNumber,
	SecondaryCCPCH-SlotFormat,
	Segment-Type,
	S-FieldLength,
	SFN,
	SFNSFNChangeLimit,
	SFNSFNDriftRate,
	SFNSFNDriftRateQuality,
	SFNSFNQuality,
	ShutdownTimer,
	SIB-Originator,
	SpecialBurstScheduling,
	SignallingBearerRequestIndicator,
	SSDT-Cell-Identity,
	SSDT-CellID-Length,
	SSDT-Indication,
	Start-Of-Audit-Sequence-Indicator,
	STTD-Indicator,
	SSDT-SupportIndicator,
	SyncCase,
	SYNCDlCodeId,
	SyncFrameNumber,
	SynchronisationReportCharacteristics,
	SynchronisationReportType,
	T-Cell,
	T-RLFAILURE,
	TDD-ChannelisationCode,
	TDD-ChannelisationCodeLCR,
	TDD-DL-Code-LCR-Information,
	TDD-DPCHOffset,
	TDD-TPC-DownlinkStepSize,
	TDD-PhysicalChannelOffset,
	TDD-UL-Code-LCR-Information,
	TFCI2-BearerInformationResponse,
	TFCI2BearerRequestIndicator,
	TFCI-Coding,
	TFCI-Presence,
	TFCI-SignallingMode,
	TFCS,
	TimeSlot,
	TimeSlotLCR,
	TimeSlotDirection,
	TimeSlotStatus,
	TimingAdjustmentValue,
	TimingAdvanceApplied,
	ToAWE,
	ToAWS,
	TransmissionDiversityApplied,
	TransmitDiversityIndicator,
	TransmissionGapPatternSequenceCodeInformation,
	Transmission-Gap-Pattern-Sequence-Information,
	TransportBearerRequestIndicator,
	TransportFormatSet,
	TransportLayerAddress,
	TSTD-Indicator,
	TUTRANGPS,
	TUTRANGPSChangeLimit,
	TUTRANGPSDriftRate,
	TUTRANGPSDriftRateQuality,
	TUTRANGPSQuality,
	UARFCN,
	UC-Id,
	USCH-Information,
	USCH-InformationResponse,
	UL-CapacityCredit,
	UL-DPCCH-SlotFormat,
	UL-SIR,
	UL-FP-Mode,
	UL-PhysCH-SF-Variation,
	UL-ScramblingCode,
	UL-Timeslot-Information,
	UL-TimeslotLCR-Information,
	UL-TimeSlot-ISCP-Info,
	UL-TimeSlot-ISCP-LCR-Info,
	UL-TimeslotISCP-Value,
	UL-TimeslotISCP-Value-IncrDecrThres,
	USCH-ID,
	HSDSCH-FDD-Information,
	HSDSCH-FDD-Information-Response,
	HSDSCH-Information-to-Modify,
	HSDSCH-MACdFlow-ID,
	HSDSCH-RNTI,
	HSDSCH-TDD-Information,
	HSDSCH-TDD-Information-Response,
	PrimaryCCPCH-RSCP,
	HSDSCH-FDD-Update-Information,
	HSDSCH-TDD-Update-Information,
	UL-Synchronisation-Parameters-LCR,
	TDD-DL-DPCH-TimeSlotFormat-LCR,
	TDD-UL-DPCH-TimeSlotFormat-LCR
FROM NBAP-IEs

	PrivateIE-Container{},
	ProtocolExtensionContainer{},
	ProtocolIE-Container{},
	ProtocolIE-Single-Container{},
	ProtocolIE-ContainerList{},
	NBAP-PRIVATE-IES,
	NBAP-PROTOCOL-IES,
	NBAP-PROTOCOL-EXTENSION
FROM NBAP-Containers

	id-Active-Pattern-Sequence-Information,
	id-AdjustmentRatio,
	id-AICH-Information,
	id-AICH-ParametersListIE-CTCH-ReconfRqstFDD,
	id-AP-AICH-Information,
	id-AP-AICH-ParametersListIE-CTCH-ReconfRqstFDD,
	id-BCH-Information,
	id-BCCH-ModificationTime,
	id-bindingID,
	id-BlockingPriorityIndicator,
	id-Cause,
	id-CauseLevel-PSCH-ReconfFailure,
	id-CauseLevel-RL-AdditionFailureFDD,
	id-CauseLevel-RL-AdditionFailureTDD,
	id-CauseLevel-RL-ReconfFailure,
	id-CauseLevel-RL-SetupFailureFDD,
	id-CauseLevel-RL-SetupFailureTDD,
	id-CauseLevel-SyncAdjustmntFailureTDD,
	id-CCP-InformationItem-AuditRsp,
	id-CCP-InformationList-AuditRsp,
	id-CCP-InformationItem-ResourceStatusInd,
	id-CCTrCH-InformationItem-RL-FailureInd,
	id-CCTrCH-InformationItem-RL-RestoreInd,
	id-CCTrCH-Initial-DL-Power-RL-AdditionRqstTDD,
	id-CCTrCH-Initial-DL-Power-RL-ReconfPrepTDD,
	id-CCTrCH-Initial-DL-Power-RL-SetupRqstTDD,
	id-CDCA-ICH-Information,
	id-CDCA-ICH-ParametersListIE-CTCH-ReconfRqstFDD,
	id-CellAdjustmentInfo-SyncAdjustmntRqstTDD,
	id-CellAdjustmentInfoItem-SyncAdjustmentRqstTDD,
	id-Cell-InformationItem-AuditRsp,
	id-Cell-InformationItem-ResourceStatusInd,
	id-Cell-InformationList-AuditRsp,
	id-CellParameterID,
	id-CellSyncBurstTransInit-CellSyncInitiationRqstTDD,
	id-CellSyncBurstMeasureInit-CellSyncInitiationRqstTDD,
	id-cellSyncBurstRepetitionPeriod,
	id-CellSyncBurstTransReconfiguration-CellSyncReconfRqstTDD,
	id-CellSyncBurstTransReconfInfo-CellSyncReconfRqstTDD,
	id-CellSyncBurstMeasReconfiguration-CellSyncReconfRqstTDD,
	id-CellSyncBurstMeasInfoList-CellSyncReconfRqstTDD,
	id-CellSyncBurstInfoList-CellSyncReconfRqstTDD,
	id-CellSyncInfo-CellSyncReprtTDD,
	id-CFN,
    id-CFNReportingIndicator,
	id-C-ID,
	id-Closed-Loop-Timing-Adjustment-Mode,
	id-CommonMeasurementAccuracy,
	id-CommonMeasurementObjectType-CM-Rprt,
	id-CommonMeasurementObjectType-CM-Rqst,
	id-CommonMeasurementObjectType-CM-Rsp,
	id-CommonMeasurementType,
	id-CommonPhysicalChannelID,
	id-CommonPhysicalChannelType-CTCH-ReconfRqstFDD,
	id-CommonPhysicalChannelType-CTCH-SetupRqstFDD,
	id-CommonPhysicalChannelType-CTCH-SetupRqstTDD,
	id-CommunicationContextInfoItem-Reset,
	id-CommunicationControlPortID,
	id-CommunicationControlPortInfoItem-Reset,
	id-Compressed-Mode-Deactivation-Flag,
	id-ConfigurationGenerationID,
	id-CPCH-Information,
	id-CPCH-Parameters-CTCH-SetupRsp,
	id-CPCH-ParametersListIE-CTCH-ReconfRqstFDD,
	id-CRNC-CommunicationContextID,
	id-CriticalityDiagnostics,
	id-CSBTransmissionID,
	id-CSBMeasurementID,
	id-DCHs-to-Add-FDD,
	id-DCHs-to-Add-TDD,
	id-DCH-AddList-RL-ReconfPrepTDD,
	id-DCH-DeleteList-RL-ReconfPrepFDD,
	id-DCH-DeleteList-RL-ReconfPrepTDD,
	id-DCH-DeleteList-RL-ReconfRqstFDD,
	id-DCH-DeleteList-RL-ReconfRqstTDD,
	id-DCH-FDD-Information,
	id-DCH-TDD-Information,
	id-DCH-InformationResponse,
	id-DCH-RearrangeList-Bearer-RearrangeInd,
	id-DSCH-RearrangeList-Bearer-RearrangeInd,
	id-FDD-DCHs-to-Modify,
	id-TDD-DCHs-to-Modify,
	id-DedicatedMeasurementObjectType-DM-Rprt,
	id-DedicatedMeasurementObjectType-DM-Rqst,
	id-DedicatedMeasurementObjectType-DM-Rsp,
	id-DedicatedMeasurementType,
	id-DelayedActivation,
	id-DelayedActivationList-RL-ActivationCmdFDD,
	id-DelayedActivationList-RL-ActivationCmdTDD,
	id-DelayedActivationInformation-RL-ActivationCmdFDD,
	id-DelayedActivationInformation-RL-ActivationCmdTDD,
	id-DL-CCTrCH-InformationAddList-RL-ReconfPrepTDD,
	id-DL-CCTrCH-InformationDeleteItem-RL-ReconfRqstTDD,
	id-DL-CCTrCH-InformationDeleteList-RL-ReconfPrepTDD,
	id-DL-CCTrCH-InformationDeleteList-RL-ReconfRqstTDD,
	id-DL-CCTrCH-InformationItem-RL-SetupRqstTDD,
	id-DL-CCTrCH-InformationList-RL-AdditionRqstTDD,
	id-DL-CCTrCH-InformationList-RL-SetupRqstTDD,
	id-DL-CCTrCH-InformationModifyItem-RL-ReconfRqstTDD,
	id-DL-CCTrCH-InformationModifyList-RL-ReconfPrepTDD,
	id-DL-CCTrCH-InformationModifyList-RL-ReconfRqstTDD,
	id-DL-DPCH-InformationAddListIE-RL-ReconfPrepTDD,
	id-DL-DPCH-InformationItem-RL-AdditionRqstTDD,
	id-DL-DPCH-InformationList-RL-SetupRqstTDD,
	id-DL-DPCH-InformationModify-AddListIE-RL-ReconfPrepTDD,
	id-DL-DPCH-InformationModify-DeleteListIE-RL-ReconfPrepTDD,
	id-DL-DPCH-InformationModify-ModifyListIE-RL-ReconfPrepTDD,
	id-DL-DPCH-Information-RL-ReconfPrepFDD,
	id-DL-DPCH-Information-RL-ReconfRqstFDD,
	id-DL-DPCH-Information-RL-SetupRqstFDD,
	id-DL-DPCH-TimingAdjustment,
	id-DL-PowerBalancing-Information,
	id-DL-PowerBalancing-ActivationIndicator,
	id-DL-ReferencePowerInformationItem-DL-PC-Rqst,
	id-DL-PowerBalancing-UpdatedIndicator,
	id-DLReferencePower,
	id-DLReferencePowerList-DL-PC-Rqst,
	id-DL-TPC-Pattern01Count,
	id-DPC-Mode,
	id-DPCHConstant,
	id-DSCH-AddItem-RL-ReconfPrepFDD,
	id-DSCHs-to-Add-FDD,
	id-DSCH-DeleteItem-RL-ReconfPrepFDD,
	id-DSCH-DeleteList-RL-ReconfPrepFDD,
	id-DSCHs-to-Add-TDD,
	id-DSCH-Information-DeleteList-RL-ReconfPrepTDD,
	id-DSCH-Information-ModifyList-RL-ReconfPrepTDD,
	id-DSCH-InformationResponse,
	id-DSCH-FDD-Information,
	id-DSCH-FDD-Common-Information,
	id-DSCH-TDD-Information,
	id-DSCH-ModifyItem-RL-ReconfPrepFDD,
	id-DSCH-ModifyList-RL-ReconfPrepFDD,
	id-End-Of-Audit-Sequence-Indicator,
	id-EnhancedDSCHPC,
	id-EnhancedDSCHPCIndicator,
	id-FACH-Information,
	id-FACH-ParametersList-CTCH-ReconfRqstTDD,
	id-FACH-ParametersList-CTCH-SetupRsp,
	id-FACH-ParametersListIE-CTCH-ReconfRqstFDD,
	id-FACH-ParametersListIE-CTCH-SetupRqstFDD,
	id-FACH-ParametersListIE-CTCH-SetupRqstTDD,
	id-IndicationType-ResourceStatusInd,
	id-InformationExchangeID,
    id-InformationExchangeObjectType-InfEx-Rqst,
    id-InformationExchangeObjectType-InfEx-Rsp,
    id-InformationExchangeObjectType-InfEx-Rprt,
    id-InformationReportCharacteristics,	
    id-InformationType,
	id-InitDL-Power,
	id-InnerLoopDLPCStatus,
	id-IntStdPhCellSyncInfoItem-CellSyncReprtTDD,
	id-IPDLParameter-Information-Cell-ReconfRqstFDD,
	id-IPDLParameter-Information-Cell-SetupRqstFDD,
	id-IPDLParameter-Information-Cell-ReconfRqstTDD,
	id-IPDLParameter-Information-Cell-SetupRqstTDD,
	id-LateEntranceCellSyncInfoItem-CellSyncReprtTDD,
	id-Limited-power-increase-information-Cell-SetupRqstFDD,
	id-Local-Cell-ID,
	id-Local-Cell-Group-InformationItem-AuditRsp,
	id-Local-Cell-Group-InformationItem-ResourceStatusInd,
	id-Local-Cell-Group-InformationItem2-ResourceStatusInd,
	id-Local-Cell-Group-InformationList-AuditRsp,
	id-Local-Cell-InformationItem-AuditRsp,
	id-Local-Cell-InformationItem-ResourceStatusInd,
	id-Local-Cell-InformationItem2-ResourceStatusInd,
	id-Local-Cell-InformationList-AuditRsp,
	id-AdjustmentPeriod,
	id-MaxAdjustmentStep,
	id-MaximumTransmissionPower,
	id-MeasurementFilterCoefficient,
	id-MeasurementID,
	id-MIB-SB-SIB-InformationList-SystemInfoUpdateRqst,
	id-NCyclesPerSFNperiod,
	id-NeighbouringCellMeasurementInformation,
	id-NodeB-CommunicationContextID,
	id-NRepetitionsPerCyclePeriod,
	id-P-CCPCH-Information,
	id-P-CPICH-Information,
	id-P-SCH-Information,
	id-PCCPCH-Information-Cell-ReconfRqstTDD,
	id-PCCPCH-Information-Cell-SetupRqstTDD,
	id-PCH-Parameters-CTCH-ReconfRqstTDD,
	id-PCH-Parameters-CTCH-SetupRsp,
	id-PCH-ParametersItem-CTCH-ReconfRqstFDD,
	id-PCH-ParametersItem-CTCH-SetupRqstFDD,
	id-PCH-ParametersItem-CTCH-SetupRqstTDD,
	id-PCH-Information,
	id-PCPCH-Information,
	id-PICH-ParametersItem-CTCH-ReconfRqstFDD,
	id-PDSCH-Information-AddListIE-PSCH-ReconfRqst,
	id-PDSCH-Information-Cell-SetupRqstFDD,
	id-PDSCH-Information-Cell-ReconfRqstFDD,
	id-PDSCH-Information-ModifyListIE-PSCH-ReconfRqst,
	id-PDSCH-RL-ID,
	id-PDSCHSets-AddList-PSCH-ReconfRqst,
	id-PDSCHSets-DeleteList-PSCH-ReconfRqst,
	id-PDSCHSets-ModifyList-PSCH-ReconfRqst,
	id-PICH-Information,
	id-PICH-Parameters-CTCH-ReconfRqstTDD,
	id-PICH-ParametersItem-CTCH-SetupRqstTDD,
	id-PowerAdjustmentType,
	id-Power-Local-Cell-Group-InformationItem-AuditRsp,
	id-Power-Local-Cell-Group-InformationItem-ResourceStatusInd,
	id-Power-Local-Cell-Group-InformationItem2-ResourceStatusInd,
	id-Power-Local-Cell-Group-InformationList-AuditRsp,
	id-Power-Local-Cell-Group-InformationList-ResourceStatusInd,
	id-Power-Local-Cell-Group-InformationList2-ResourceStatusInd,
	id-Power-Local-Cell-Group-ID,
	id-PRACH-Information,
	id-PRACHConstant,
	id-PRACH-ParametersItem-CTCH-SetupRqstTDD,
	id-PRACH-ParametersListIE-CTCH-ReconfRqstFDD,
	id-PrimaryCCPCH-Information-Cell-ReconfRqstFDD,
	id-PrimaryCCPCH-Information-Cell-SetupRqstFDD,
	id-PrimaryCPICH-Information-Cell-ReconfRqstFDD,
	id-PrimaryCPICH-Information-Cell-SetupRqstFDD,
	id-PrimarySCH-Information-Cell-ReconfRqstFDD,
	id-PrimarySCH-Information-Cell-SetupRqstFDD,
	id-PrimaryScramblingCode,
	id-SCH-Information-Cell-ReconfRqstTDD,
	id-SCH-Information-Cell-SetupRqstTDD,
	id-PUSCH-Information-AddListIE-PSCH-ReconfRqst,
	id-PUSCH-Information-ModifyListIE-PSCH-ReconfRqst,
	id-PUSCHConstant,
	id-PUSCHSets-AddList-PSCH-ReconfRqst,
	id-PUSCHSets-DeleteList-PSCH-ReconfRqst,
	id-PUSCHSets-ModifyList-PSCH-ReconfRqst,
	id-Qth-Parameter,
	id-RACH-Information,
	id-RACH-Parameters-CTCH-SetupRsp,
	id-RACH-ParametersItem-CTCH-SetupRqstFDD,
	id-RACH-ParameterItem-CTCH-SetupRqstTDD,
	id-ReferenceClockAvailability,
	id-ReferenceSFNoffset,
	id-ReportCharacteristics,
	id-Reporting-Object-RL-FailureInd,
	id-Reporting-Object-RL-RestoreInd,
	id-ResetIndicator,
	id-RL-InformationItem-DM-Rprt,
	id-RL-InformationItem-DM-Rqst,
	id-RL-InformationItem-DM-Rsp,
	id-RL-InformationItem-RL-AdditionRqstFDD,
	id-RL-informationItem-RL-DeletionRqst,
	id-RL-InformationItem-RL-FailureInd,
	id-RL-InformationItem-RL-PreemptRequiredInd,
	id-RL-InformationItem-RL-ReconfPrepFDD,
	id-RL-InformationItem-RL-ReconfRqstFDD,
	id-RL-InformationItem-RL-RestoreInd,
	id-RL-InformationItem-RL-SetupRqstFDD,
	id-RL-InformationList-RL-AdditionRqstFDD,
	id-RL-informationList-RL-DeletionRqst,
	id-RL-InformationList-RL-PreemptRequiredInd,
	id-RL-InformationList-RL-ReconfPrepFDD,
	id-RL-InformationList-RL-ReconfRqstFDD,
	id-RL-InformationList-RL-SetupRqstFDD,
	id-RL-InformationResponseItem-RL-AdditionRspFDD,
	id-RL-InformationResponseItem-RL-ReconfReady,
	id-RL-InformationResponseItem-RL-ReconfRsp,
	id-RL-InformationResponseItem-RL-SetupRspFDD,
	id-RL-InformationResponseList-RL-AdditionRspFDD,
	id-RL-InformationResponseList-RL-ReconfReady,
	id-RL-InformationResponseList-RL-ReconfRsp,
	id-RL-InformationResponseList-RL-SetupRspFDD,
	id-RL-InformationResponse-RL-AdditionRspTDD,
	id-RL-InformationResponse-RL-SetupRspTDD,
	id-RL-Information-RL-AdditionRqstTDD,
	id-RL-Information-RL-ReconfRqstTDD,
	id-RL-Information-RL-ReconfPrepTDD,
	id-RL-Information-RL-SetupRqstTDD,
	id-RL-ReconfigurationFailureItem-RL-ReconfFailure,
	id-RL-Set-InformationItem-DM-Rprt,
	id-RL-Set-InformationItem-DM-Rsp,
	id-RL-Set-InformationItem-RL-FailureInd,
	id-RL-Set-InformationItem-RL-RestoreInd,
	id-RL-Specific-DCH-Info,
	id-S-CCPCH-Information,
	id-S-CPICH-Information,
	id-SCH-Information,
	id-S-SCH-Information,
	id-Secondary-CCPCHListIE-CTCH-ReconfRqstTDD,
	id-Secondary-CCPCH-parameterListIE-CTCH-SetupRqstTDD,
	id-Secondary-CCPCH-Parameters-CTCH-ReconfRqstTDD,
	id-SecondaryCPICH-InformationItem-Cell-ReconfRqstFDD,
	id-SecondaryCPICH-InformationItem-Cell-SetupRqstFDD,
	id-SecondaryCPICH-InformationList-Cell-ReconfRqstFDD,
	id-SecondaryCPICH-InformationList-Cell-SetupRqstFDD,
	id-SecondarySCH-Information-Cell-ReconfRqstFDD,
	id-SecondarySCH-Information-Cell-SetupRqstFDD,
	id-SegmentInformationListIE-SystemInfoUpdate,
	id-SFN,
    id-SFNReportingIndicator,
	id-ShutdownTimer,
	id-SignallingBearerRequestIndicator,
	id-SSDT-CellIDforEDSCHPC,
	id-Start-Of-Audit-Sequence-Indicator,
	id-Successful-RL-InformationRespItem-RL-AdditionFailureFDD,
	id-Successful-RL-InformationRespItem-RL-SetupFailureFDD,
	id-Synchronisation-Configuration-Cell-ReconfRqst,
	id-Synchronisation-Configuration-Cell-SetupRqst,
	id-SyncCase,
	id-SyncCaseIndicatorItem-Cell-SetupRqstTDD-PSCH,
	id-SyncFrameNumber,
	id-SynchronisationReportType,
	id-SynchronisationReportCharacteristics,
	id-SyncReportType-CellSyncReprtTDD,
	id-T-Cell,
	id-TargetCommunicationControlPortID,
	id-TFCI2-Bearer-Information-RL-SetupRqstFDD,
	id-TFCI2-BearerInformationResponse,
	id-TFCI2BearerRequestIndicator,
	id-TFCI2-BearerSpecificInformation-RL-ReconfPrepFDD,
	id-Transmission-Gap-Pattern-Sequence-Information,
	id-TimeSlotConfigurationList-Cell-ReconfRqstTDD,
	id-TimeSlotConfigurationList-Cell-SetupRqstTDD,
	id-timeslotInfo-CellSyncInitiationRqstTDD,
	id-TimeslotISCPInfo,
	id-TimingAdvanceApplied,
	id-TransmissionDiversityApplied,
	id-transportlayeraddress,
	id-UARFCNforNt,
	id-UARFCNforNd,
	id-UARFCNforNu,
	id-UL-CCTrCH-InformationAddList-RL-ReconfPrepTDD,
	id-UL-CCTrCH-InformationDeleteItem-RL-ReconfRqstTDD,
	id-UL-CCTrCH-InformationDeleteList-RL-ReconfPrepTDD,
	id-UL-CCTrCH-InformationDeleteList-RL-ReconfRqstTDD,
	id-UL-CCTrCH-InformationItem-RL-SetupRqstTDD,
	id-UL-CCTrCH-InformationList-RL-AdditionRqstTDD,
	id-UL-CCTrCH-InformationList-RL-SetupRqstTDD,
	id-UL-CCTrCH-InformationModifyItem-RL-ReconfRqstTDD,
	id-UL-CCTrCH-InformationModifyList-RL-ReconfPrepTDD,
	id-UL-CCTrCH-InformationModifyList-RL-ReconfRqstTDD,
	id-UL-DPCH-InformationAddListIE-RL-ReconfPrepTDD,
	id-UL-DPCH-InformationItem-RL-AdditionRqstTDD,
	id-UL-DPCH-InformationList-RL-SetupRqstTDD,
	id-UL-DPCH-InformationModify-AddListIE-RL-ReconfPrepTDD,
	id-UL-DPCH-InformationModify-DeleteListIE-RL-ReconfPrepTDD,
	id-UL-DPCH-InformationModify-ModifyListIE-RL-ReconfPrepTDD,
	id-UL-DPCH-Information-RL-ReconfPrepFDD,
	id-UL-DPCH-Information-RL-ReconfRqstFDD,
	id-UL-DPCH-Information-RL-SetupRqstFDD,
	id-Unsuccessful-cell-InformationRespItem-SyncAdjustmntFailureTDD,
	id-Unsuccessful-PDSCHSetItem-PSCH-ReconfFailureTDD,
	id-Unsuccessful-PUSCHSetItem-PSCH-ReconfFailureTDD,
	id-Unsuccessful-RL-InformationRespItem-RL-AdditionFailureFDD,
	id-Unsuccessful-RL-InformationRespItem-RL-SetupFailureFDD,
	id-Unsuccessful-RL-InformationResp-RL-AdditionFailureTDD,
	id-Unsuccessful-RL-InformationResp-RL-SetupFailureTDD,
	id-USCH-Information-Add,
	id-USCH-Information-DeleteList-RL-ReconfPrepTDD,
	id-USCH-Information-ModifyList-RL-ReconfPrepTDD,
	id-USCH-InformationResponse,
	id-USCH-Information,
	id-USCH-RearrangeList-Bearer-RearrangeInd,
	id-DL-DPCH-LCR-Information-RL-SetupRqstTDD,
 id-DwPCH-LCR-Information	,
 id-DwPCH-LCR-InformationList-AuditRsp,
 id-DwPCH-LCR-Information-Cell-SetupRqstTDD,
 id-DwPCH-LCR-Information-Cell-ReconfRqstTDD,
 id-DwPCH-LCR-Information-ResourceStatusInd,
 id-maxFACH-Power-LCR-CTCH-SetupRqstTDD,
 id-maxFACH-Power-LCR-CTCH-ReconfRqstTDD,
 id-FPACH-LCR-Information,
 id-FPACH-LCR-Information-AuditRsp,
 id-FPACH-LCR-InformationList-AuditRsp,
 id-FPACH-LCR-InformationList-ResourceStatusInd,
	id-FPACH-LCR-Parameters-CTCH-SetupRqstTDD, 
 id-FPACH-LCR-Parameters-CTCH-ReconfRqstTDD,
 id-PCCPCH-LCR-Information-Cell-SetupRqstTDD,
	id-PCH-Power-LCR-CTCH-SetupRqstTDD,
	id-PCH-Power-LCR-CTCH-ReconfRqstTDD,
	id-PICH-LCR-Parameters-CTCH-SetupRqstTDD,
  	id-PRACH-LCR-ParametersList-CTCH-SetupRqstTDD, 
 id-RL-InformationResponse-LCR-RL-SetupRspTDD	,
 id-Secondary-CCPCH-LCR-parameterList-CTCH-SetupRqstTDD,
	id-TimeSlot,
 id-TimeSlotConfigurationList-LCR-Cell-ReconfRqstTDD,
 id-TimeSlotConfigurationList-LCR-Cell-SetupRqstTDD,
	id-TimeslotISCP-LCR-InfoList-RL-SetupRqstTDD,
	id-TimeSlotLCR-CM-Rqst,
 id-UL-DPCH-LCR-Information-RL-SetupRqstTDD,
	id-DL-DPCH-InformationItem-LCR-RL-AdditionRqstTDD,
	id-UL-DPCH-InformationItem-LCR-RL-AdditionRqstTDD,
	id-TimeslotISCP-InformationList-LCR-RL-AdditionRqstTDD,
	id-DL-DPCH-LCR-InformationAddList-RL-ReconfPrepTDD,
	id-DL-DPCH-LCR-InformationModify-AddList-RL-ReconfPrepTDD,
	id-DL-Timeslot-LCR-InformationModify-ModifyList-RL-ReconfPrepTDD,
	id-TimeslotISCPInfoList-LCR-DL-PC-RqstTDD,
	id-UL-DPCH-LCR-InformationAddListIE-RL-ReconfPrepTDD,
	id-UL-DPCH-LCR-InformationModify-AddList,
	id-UL-TimeslotLCR-Information-RL-ReconfPrepTDD,
	id-UL-SIRTarget,
	id-PDSCH-AddInformation-LCR-PSCH-ReconfRqst,
	id-PDSCH-AddInformation-LCR-AddListIE-PSCH-ReconfRqst,
	id-PDSCH-ModifyInformation-LCR-PSCH-ReconfRqst,
	id-PDSCH-ModifyInformation-LCR-ModifyListIE-PSCH-ReconfRqst,
	id-PUSCH-AddInformation-LCR-PSCH-ReconfRqst,
	id-PUSCH-AddInformation-LCR-AddListIE-PSCH-ReconfRqst,
	id-PUSCH-ModifyInformation-LCR-PSCH-ReconfRqst,
	id-PUSCH-ModifyInformation-LCR-ModifyListIE-PSCH-ReconfRqst,
	id-PUSCH-Info-DM-Rqst,
	id-PUSCH-Info-DM-Rsp,
	id-PUSCH-Info-DM-Rprt,
	id-RL-InformationResponse-LCR-RL-AdditionRspTDD,
	id-IPDLParameter-Information-LCR-Cell-SetupRqstTDD,
	id-IPDLParameter-Information-LCR-Cell-ReconfRqstTDD,
	id-HS-PDSCH-HS-SCCH-MaxPower-PSCH-ReconfRqst,
	id-HS-PDSCH-HS-SCCH-ScramblingCode-PSCH-ReconfRqst,
	id-HS-PDSCH-FDD-Code-Information-PSCH-ReconfRqst,
	id-HS-SCCH-FDD-Code-Information-PSCH-ReconfRqst,
	id-HS-PDSCH-TDD-Information-PSCH-ReconfRqst,
	id-Add-To-HS-SCCH-Resource-Pool-PSCH-ReconfRqst,
	id-Modify-HS-SCCH-Resource-Pool-PSCH-ReconfRqst,
	id-Delete-From-HS-SCCH-Resource-Pool-PSCH-ReconfRqst,
	id-SYNCDlCodeId-TransInitLCR-CellSyncInitiationRqstTDD,
	id-SYNCDlCodeId-MeasureInitLCR-CellSyncInitiationRqstTDD,
	id-SYNCDlCodeIdTransReconfInfoLCR-CellSyncReconfRqstTDD,
	id-SYNCDlCodeIdMeasReconfigurationLCR-CellSyncReconfRqstTDD,
	id-SYNCDlCodeIdMeasInfoList-CellSyncReconfRqstTDD,
	id-SyncDLCodeIdsMeasInfoList-CellSyncReprtTDD,
	id-NSubCyclesPerCyclePeriod-CellSyncReconfRqstTDD,
	id-DwPCH-Power,
	id-AccumulatedClockupdate-CellSyncReprtTDD,
	id-HSDSCH-FDD-Information,
	id-HSDSCH-FDD-Information-Response,
	id-HSDSCH-FDD-Information-to-Add,
	id-HSDSCH-FDD-Information-to-Delete,
	id-HSDSCH-Information-to-Modify,
	id-HSDSCH-RearrangeList-Bearer-RearrangeInd,
	id-HSDSCH-RNTI,
	id-HSDSCH-TDD-Information,
	id-HSDSCH-TDD-Information-Response,
	id-HSDSCH-TDD-Information-Response-LCR,
	id-HSDSCH-TDD-Information-to-Add,
	id-HSDSCH-TDD-Information-to-Delete,
	id-HSPDSCH-RL-ID,
	id-PrimCCPCH-RSCP-DL-PC-RqstTDD,
	id-HSDSCH-FDD-Update-Information,
	id-HSDSCH-TDD-Update-Information,
	id-UL-Synchronisation-Parameters-LCR,
id-DL-DPCH-TimeSlotFormat-LCR-ModifyItem-RL-ReconfPrepTDD,
id-UL-DPCH-TimeSlotFormat-LCR-ModifyItem-RL-ReconfPrepTDD,

	maxNrOfCCTrCHs,
	maxNrOfCellSyncBursts,
	maxNrOfCodes,
	maxNrOfCPCHs,
	maxNrOfDCHs,
	maxNrOfDLTSs,
	maxNrOfDLTSLCRs,
	maxNrOfDPCHs,
	maxNrOfDSCHs,
	maxNrOfFACHs,
	maxNrOfRLs,
	maxNrOfRLs-1,
	maxNrOfRLs-2,
	maxNrOfRLSets,
	maxNrOfPCPCHs,
	maxNrOfPDSCHs,
	maxNrOfPUSCHs,
	maxNrOfPRACHLCRs,
	maxNrOfPDSCHSets,
	maxNrOfPUSCHSets,
	maxNrOfReceptsPerSyncFrame,
	maxNrOfSCCPCHs,
	maxNrOfSCCPCHLCRs,
	maxNrOfULTSs,
	maxNrOfULTSLCRs,
	maxNrOfUSCHs,
	maxAPSigNum,
	maxCPCHCell,
	maxFACHCell,
	maxFPACHCell,
	maxNoofLen,
	maxRACHCell,
	maxPCPCHCell,
	maxPRACHCell,
	maxSCCPCHCell,
	maxSCPICHCell,
	maxCellinNodeB,
	maxCCPinNodeB,
	maxCommunicationContext,
	maxLocalCellinNodeB,
	maxNrOfSlotFormatsPRACH,
	maxIB,
	maxIBSEG,
	maxNrOfHSSCCHs,
	maxNrOfSyncFramesLCR,
	maxNrOfReceptionsperSyncFrameLCR,
	maxNrOfSyncDLCodesLCR,
	maxNrOfMACdFlows
FROM NBAP-Constants;

-- **************************************************************
--
-- COMMON TRANSPORT CHANNEL SETUP REQUEST FDD
--
-- **************************************************************

CommonTransportChannelSetupRequestFDD ::= SEQUENCE {
	protocolIEs				ProtocolIE-Container	{{CommonTransportChannelSetupRequestFDD-IEs}},
	protocolExtensions		ProtocolExtensionContainer	{{CommonTransportChannelSetupRequestFDD-Extensions}}     OPTIONAL,
	...
}

CommonTransportChannelSetupRequestFDD-Extensions NBAP-PROTOCOL-EXTENSION ::= {
	...
}

CommonTransportChannelSetupRequestFDD-IEs NBAP-PROTOCOL-IES ::= {
	{ ID	id-C-ID	CRITICALITY   reject	TYPE	C-ID	PRESENCE	mandatory	}|
	{ ID	id-ConfigurationGenerationID	CRITICALITY		reject		TYPE	ConfigurationGenerationID						PRESENCE 	mandatory	}|
	{ ID	id-CommonPhysicalChannelType-CTCH-SetupRqstFDD		CRITICALITY 	ignore		TYPE	CommonPhysicalChannelType-CTCH-SetupRqstFDD		PRESENCE 	mandatory	},
	...
}

CommonPhysicalChannelType-CTCH-SetupRqstFDD ::= CHOICE {
	secondary-CCPCH-parameters		Secondary-CCPCH-CTCH-SetupRqstFDD,
	pRACH-parameters				PRACH-CTCH-SetupRqstFDD,
	pCPCHes-parameters				PCPCH-CTCH-SetupRqstFDD,
	...
}

Secondary-CCPCH-CTCH-SetupRqstFDD ::= SEQUENCE {
	commonPhysicalChannelID					CommonPhysicalChannelID,
	fdd-S-CCPCH-Offset						FDD-S-CCPCH-Offset,
	dl-ScramblingCode						DL-ScramblingCode	OPTIONAL,
	-- This IE shall be present if the PCH Parameters IE is not present
	fdd-DL-ChannelisationCodeNumber			FDD-DL-ChannelisationCodeNumber,
	tFCS			TFCS,
	secondary-CCPCH-SlotFormat				SecondaryCCPCH-SlotFormat,
	tFCI-Presence							TFCI-Presence	OPTIONAL,
	-- This IE shall be present if the Secondary CCPCH Slot Format is set to any of the values from 8 to 17
	multiplexingPosition					MultiplexingPosition,
	powerOffsetInformation					PowerOffsetInformation-CTCH-SetupRqstFDD,
	sTTD-Indicator							STTD-Indicator,
	fACH-Parameters							FACH-ParametersList-CTCH-SetupRqstFDD		OPTIONAL,
	pCH-Parameters							PCH-Parameters-CTCH-SetupRqstFDD			OPTIONAL,
	iE-Extensions							ProtocolExtensionContainer  { { Secondary-CCPCHItem-CTCH-SetupRqstFDD-ExtIEs} }		OPTIONAL,
	...
}

Secondary-CCPCHItem-CTCH-SetupRqstFDD-ExtIEs NBAP-PROTOCOL-EXTENSION ::= {
	...
}

PowerOffsetInformation-CTCH-SetupRqstFDD ::= SEQUENCE {
	pO1-ForTFCI-Bits						PowerOffset,
	pO3-ForPilotBits						PowerOffset,
	iE-Extensions							ProtocolExtensionContainer { { PowerOffsetInformation-CTCH-SetupRqstFDD-ExtIEs} }	OPTIONAL,
	...
}

PowerOffsetInformation-CTCH-SetupRqstFDD-ExtIEs NBAP-PROTOCOL-EXTENSION ::= {
	...
}

FACH-ParametersList-CTCH-SetupRqstFDD ::= ProtocolIE-Single-Container {{ FACH-ParametersListIEs-CTCH-SetupRqstFDD }}

FACH-ParametersListIEs-CTCH-SetupRqstFDD NBAP-PROTOCOL-IES ::= {
	{ ID id-FACH-ParametersListIE-CTCH-SetupRqstFDD   CRITICALITY reject	TYPE FACH-ParametersListIE-CTCH-SetupRqstFDD	PRESENCE mandatory }
}

FACH-ParametersListIE-CTCH-SetupRqstFDD ::= SEQUENCE (SIZE (1..maxNrOfFACHs)) OF FACH-ParametersItem-CTCH-SetupRqstFDD

FACH-ParametersItem-CTCH-SetupRqstFDD ::= SEQUENCE {
	commonTransportChannelID			CommonTransportChannelID,
	transportFormatSet					TransportFormatSet,
	toAWS								ToAWS,
	toAWE								ToAWE,
	maxFACH-Power						DL-Power,
	iE-Extensions						ProtocolExtensionContainer  { { FACH-ParametersItem-CTCH-SetupRqstFDD-ExtIEs} }		OPTIONAL,
	...
}

FACH-ParametersItem-CTCH-SetupRqstFDD-ExtIEs NBAP-PROTOCOL-EXTENSION ::= {
{ ID	id-bindingID						CRITICALITY	ignore		EXTENSION 	BindingID		PRESENCE 	optional	}|
{ ID	id-transportlayeraddress			CRITICALITY	ignore		EXTENSION 	TransportLayerAddress		PRESENCE 	optional	},
	...
}

PCH-Parameters-CTCH-SetupRqstFDD ::= ProtocolIE-Single-Container {{ PCH-ParametersIE-CTCH-SetupRqstFDD }}

PCH-ParametersIE-CTCH-SetupRqstFDD NBAP-PROTOCOL-IES ::= {
	{ ID id-PCH-ParametersItem-CTCH-SetupRqstFDD   CRITICALITY reject	TYPE PCH-ParametersItem-CTCH-SetupRqstFDD	PRESENCE mandatory }
}

PCH-ParametersItem-CTCH-SetupRqstFDD ::= SEQUENCE {
	commonTransportChannelID			CommonTransportChannelID,
	transportFormatSet					TransportFormatSet,
	toAWS								ToAWS,
	toAWE								ToAWE,	
	pCH-Power							DL-Power,
	pICH-Parameters							PICH-Parameters-CTCH-SetupRqstFDD,
	iE-Extensions						ProtocolExtensionContainer  { { PCH-ParametersItem-CTCH-SetupRqstFDD-ExtIEs} }		OPTIONAL,
	...
}

PCH-ParametersItem-CTCH-SetupRqstFDD-ExtIEs NBAP-PROTOCOL-EXTENSION ::= {
	{ ID	id-bindingID						CRITICALITY	ignore		EXTENSION 	BindingID		PRESENCE 	optional	}|
	{ ID	id-transportlayeraddress			CRITICALITY	ignore		EXTENSION 	TransportLayerAddress		PRESENCE 	optional	},
	...
}

PICH-Parameters-CTCH-SetupRqstFDD ::= SEQUENCE {
	commonPhysicalChannelID						CommonPhysicalChannelID,
	fdd-dl-ChannelisationCodeNumber				FDD-DL-ChannelisationCodeNumber,
	pICH-Power									PICH-Power,
	pICH-Mode									PICH-Mode,	
	sTTD-Indicator								STTD-Indicator,
	iE-Extensions								ProtocolExtensionContainer { { PICH-Parameters-CTCH-SetupRqstFDD-ExtIEs} }		OPTIONAL,
	...
}

PICH-Parameters-CTCH-SetupRqstFDD-ExtIEs NBAP-PROTOCOL-EXTENSION ::= {
	...
}

PRACH-CTCH-SetupRqstFDD ::= SEQUENCE {
	commonPhysicalChannelID						CommonPhysicalChannelID,
	scramblingCodeNumber					ScramblingCodeNumber,
	tFCS										TFCS,
	preambleSignatures							PreambleSignatures,
	allowedSlotFormatInformation				AllowedSlotFormatInformationList-CTCH-SetupRqstFDD,
	rACH-SubChannelNumbers						RACH-SubChannelNumbers,
	ul-punctureLimit							PunctureLimit,
	preambleThreshold							PreambleThreshold,
	rACH-Parameters								RACH-Parameters-CTCH-SetupRqstFDD,
    aICH-Parameters                             AICH-Parameters-CTCH-SetupRqstFDD,
	iE-Extensions								ProtocolExtensionContainer { { PRACHItem-CTCH-SetupRqstFDD-ExtIEs} }		OPTIONAL,
	...
}

PRACHItem-CTCH-SetupRqstFDD-ExtIEs NBAP-PROTOCOL-EXTENSION ::= {
	...
}

AllowedSlotFormatInformationList-CTCH-SetupRqstFDD ::= SEQUENCE (SIZE (1.. maxNrOfSlotFormatsPRACH)) OF AllowedSlotFormatInformationItem-CTCH-SetupRqstFDD

AllowedSlotFormatInformationItem-CTCH-SetupRqstFDD ::= SEQUENCE {
	rACHSlotFormat								RACH-SlotFormat,
	iE-Extensions								ProtocolExtensionContainer  { { AllowedSlotFormatInformationItem-CTCH-SetupRqstFDD-ExtIEs} }		OPTIONAL,
	...
}

AllowedSlotFormatInformationItem-CTCH-SetupRqstFDD-ExtIEs NBAP-PROTOCOL-EXTENSION ::= {
	...
}

RACH-Parameters-CTCH-SetupRqstFDD ::= ProtocolIE-Single-Container {{ RACH-ParametersIE-CTCH-SetupRqstFDD }}

RACH-ParametersIE-CTCH-SetupRqstFDD NBAP-PROTOCOL-IES ::= {
	{ ID id-RACH-ParametersItem-CTCH-SetupRqstFDD   CRITICALITY reject	TYPE RACH-ParametersItem-CTCH-SetupRqstFDD	PRESENCE mandatory }
}

RACH-ParametersItem-CTCH-SetupRqstFDD ::= SEQUENCE {
 	commonTransportChannelID					CommonTransportChannelID,
 	transportFormatSet							TransportFormatSet,
	iE-Extensions								ProtocolExtensionContainer  { { RACH-ParametersItem-CTCH-SetupRqstFDD-ExtIEs} }		OPTIONAL,
	...
 }

RACH-ParametersItem-CTCH-SetupRqstFDD-ExtIEs NBAP-PROTOCOL-EXTENSION ::= {
	{ ID	id-bindingID						CRITICALITY	ignore		EXTENSION 	BindingID		PRESENCE 	optional	}|
	{ ID	id-transportlayeraddress			CRITICALITY	ignore		EXTENSION 	TransportLayerAddress		PRESENCE 	optional	},
	...
}

AICH-Parameters-CTCH-SetupRqstFDD ::= SEQUENCE {
	commonPhysicalChannelID						CommonPhysicalChannelID,
	aICH-TransmissionTiming						AICH-TransmissionTiming,
	fdd-dl-ChannelisationCodeNumber				FDD-DL-ChannelisationCodeNumber,
	aICH-Power									AICH-Power,
	sTTD-Indicator								STTD-Indicator,
	iE-Extensions								ProtocolExtensionContainer  { { AICH-Parameters-CTCH-SetupRqstFDD-ExtIEs} }		OPTIONAL,
	...
}

AICH-Parameters-CTCH-SetupRqstFDD-ExtIEs NBAP-PROTOCOL-EXTENSION ::= {
	...
}

PCPCH-CTCH-SetupRqstFDD ::= SEQUENCE {
	cPCH-Parameters					CPCH-Parameters-CTCH-SetupRqstFDD,
	iE-Extensions					ProtocolExtensionContainer { { PCPCHItem-CTCH-SetupRqstFDD-ExtIEs} }		OPTIONAL,
	...
}

PCPCHItem-CTCH-SetupRqstFDD-ExtIEs NBAP-PROTOCOL-EXTENSION ::= {
	...
}

CPCH-Parameters-CTCH-SetupRqstFDD ::= SEQUENCE {
	commonTransportChannelID		CommonTransportChannelID,
	transportFormatSet				TransportFormatSet,
	aPPreambleScramblingCode 		CPCHScramblingCodeNumber,
	cDPreambleScramblingCode 		CPCHScramblingCodeNumber,
	tFCS							TFCS,
	cDSignatures 					PreambleSignatures 			OPTIONAL,
	cDSubChannelNumbers 			CDSubChannelNumbers			OPTIONAL,
	punctureLimit 					PunctureLimit,
	cPCH-UL-DPCCH-SlotFormat 		CPCH-UL-DPCCH-SlotFormat,
	uL-SIR							UL-SIR,
	initialDL-transmissionPower		DL-Power,
    maximumDLPower					DL-Power,
    minimumDLPower					DL-Power,
	pO2-ForTPC-Bits					PowerOffset,
	fDD-TPC-DownlinkStepSize	 	FDD-TPC-DownlinkStepSize,
	nStartMessage 					NStartMessage,
	nEOT							NEOT,
	channel-Assignment-Indication 	Channel-Assignment-Indication,
	cPCH-Allowed-Total-Rate			CPCH-Allowed-Total-Rate,
	pCPCHChannelInfomation			PCPCHChannelInformationList-CTCH-SetupRqstFDD,
	vCAMMapping-Information			VCAMMapping-InformationList-CTCH-SetupRqstFDD		OPTIONAL,
	-- this IE shall be present if the Channel Assignment Indication is set to "CA Active” --
	aP-AICH-Parameters				AP-AICH-Parameters-CTCH-SetupRqstFDD,
	cDCA-ICH-Parameters				CDCA-ICH-Parameters-CTCH-SetupRqstFDD,
	iE-Extensions					ProtocolExtensionContainer  { { CPCH-Parameters-CTCH-SetupRqstFDD-ExtIEs} }		OPTIONAL,
	...
}

CPCH-Parameters-CTCH-SetupRqstFDD-ExtIEs NBAP-PROTOCOL-EXTENSION ::= {
	{ ID	id-bindingID						CRITICALITY	ignore		EXTENSION 	BindingID		PRESENCE 	optional	}|
	{ ID	id-transportlayeraddress			CRITICALITY	ignore		EXTENSION 	TransportLayerAddress		PRESENCE 	optional	},
	...
}

PCPCHChannelInformationList-CTCH-SetupRqstFDD ::= SEQUENCE (SIZE (1..maxNrOfPCPCHs)) OF PCPCHChannelInformationItem-CTCH-SetupRqstFDD

PCPCHChannelInformationItem-CTCH-SetupRqstFDD ::= SEQUENCE {
	commonPhysicalChannelID				CommonPhysicalChannelID,
	cPCHScramblingCodeNumber			CPCHScramblingCodeNumber,
	dL-ScramblingCode					DL-ScramblingCode,
	fdd-dl-ChannelisationCodeNumber		FDD-DL-ChannelisationCodeNumber,
	pCP-Length							PCP-Length,
	uCSM-Information					UCSM-Information-CTCH-SetupRqstFDD		OPTIONAL,
	-- this IE shall be present if the Channel Assignment Indication is equal to "CA Inactive” --
	iE-Extensions						ProtocolExtensionContainer  { { PCPCHChannelInformationItem-CTCH-SetupRqstFDD-ExtIEs} }		OPTIONAL,
	...
}

PCPCHChannelInformationItem-CTCH-SetupRqstFDD-ExtIEs NBAP-PROTOCOL-EXTENSION ::= {
	...
}

UCSM-Information-CTCH-SetupRqstFDD ::= SEQUENCE {
	minUL-ChannelisationCodeLength		MinUL-ChannelisationCodeLength,
	nFmax 								NFmax,
	channelRequestParameters	 		ChannelRequestParametersList-CTCH-SetupRqstFDD		OPTIONAL,
	iE-Extensions						ProtocolExtensionContainer  { { UCSM-InformationItem-CTCH-SetupRqstFDD-ExtIEs} }		OPTIONAL,
	...
 }

UCSM-InformationItem-CTCH-SetupRqstFDD-ExtIEs NBAP-PROTOCOL-EXTENSION ::= {
	...
}

ChannelRequestParametersList-CTCH-SetupRqstFDD ::= SEQUENCE (SIZE (1..maxAPSigNum)) OF ChannelRequestParametersItem-CTCH-SetupRqstFDD

ChannelRequestParametersItem-CTCH-SetupRqstFDD ::= SEQUENCE {
	aPPreambleSignature 		APPreambleSignature,
	aPSubChannelNumber 			APSubChannelNumber		OPTIONAL,
	iE-Extensions				ProtocolExtensionContainer  { { ChannelRequestParametersItem-CTCH-SetupRqstFDD-ExtIEs} }		OPTIONAL,
	...
}

ChannelRequestParametersItem-CTCH-SetupRqstFDD-ExtIEs NBAP-PROTOCOL-EXTENSION ::= {
	...
}

VCAMMapping-InformationList-CTCH-SetupRqstFDD ::= SEQUENCE (SIZE (1..maxNoofLen)) OF VCAMMapping-InformationItem-CTCH-SetupRqstFDD

VCAMMapping-InformationItem-CTCH-SetupRqstFDD  ::= SEQUENCE {
	minUL-ChannelisationCodeLength		MinUL-ChannelisationCodeLength,
	nFmax 								NFmax,
	max-Number-of-PCPCHes 				Max-Number-of-PCPCHes,
	sFRequestParameters	 				SFRequestParametersList-CTCH-SetupRqstFDD,
	iE-Extensions						ProtocolExtensionContainer  { { VCAMMapping-InformationItem-CTCH-SetupRqstFDD-ExtIEs} }		OPTIONAL,
	...
}

VCAMMapping-InformationItem-CTCH-SetupRqstFDD-ExtIEs NBAP-PROTOCOL-EXTENSION ::= {
	...
}

SFRequestParametersList-CTCH-SetupRqstFDD ::= SEQUENCE (SIZE (1..maxAPSigNum)) OF SFRequestParametersItem-CTCH-SetupRqstFDD

SFRequestParametersItem-CTCH-SetupRqstFDD ::= SEQUENCE {
	aPPreambleSignature 		APPreambleSignature,
	aPSubChannelNumber 			APSubChannelNumber		OPTIONAL,
	iE-Extensions				ProtocolExtensionContainer  { { SFRequestParametersItem-CTCH-SetupRqstFDD-ExtIEs} }		OPTIONAL,
	...
}

SFRequestParametersItem-CTCH-SetupRqstFDD-ExtIEs NBAP-PROTOCOL-EXTENSION::= {
	...
}

AP-AICH-Parameters-CTCH-SetupRqstFDD ::= SEQUENCE {
	commonPhysicalChannelID						CommonPhysicalChannelID,
	fdd-dl-ChannelisationCodeNumber				FDD-DL-ChannelisationCodeNumber,
	aP-AICH-Power								AICH-Power,
	cSICH-Power									AICH-Power,
	sTTD-Indicator								STTD-Indicator,
	iE-Extensions								ProtocolExtensionContainer  { { AP-AICH-Parameters-CTCH-SetupRqstFDD-ExtIEs} }		OPTIONAL,
	...
}

AP-AICH-Parameters-CTCH-SetupRqstFDD-ExtIEs NBAP-PROTOCOL-EXTENSION ::= {
	...
}

CDCA-ICH-Parameters-CTCH-SetupRqstFDD ::= SEQUENCE {
	commonPhysicalChannelID						CommonPhysicalChannelID,
	fdd-dl-ChannelisationCodeNumber				FDD-DL-ChannelisationCodeNumber,
	cDCA-ICH-Power								AICH-Power,
	sTTD-Indicator								STTD-Indicator,
	iE-Extensions								ProtocolExtensionContainer  { { CDCA-ICH-Parameters-CTCH-SetupRqstFDD-ExtIEs} }		OPTIONAL,
	...
}

CDCA-ICH-Parameters-CTCH-SetupRqstFDD-ExtIEs NBAP-PROTOCOL-EXTENSION ::= {
	...
}

-- **************************************************************
--
-- COMMON TRANSPORT CHANNEL SETUP REQUEST TDD
--
-- **************************************************************

CommonTransportChannelSetupRequestTDD ::= SEQUENCE {
	protocolIEs				ProtocolIE-Container	{{CommonTransportChannelSetupRequestTDD-IEs}},
	protocolExtensions 		ProtocolExtensionContainer	{{CommonTransportChannelSetupRequestTDD-Extensions}}		OPTIONAL,
	...
}

CommonTransportChannelSetupRequestTDD-IEs NBAP-PROTOCOL-IES ::= {
	{ ID	id-C-ID													CRITICALITY	reject		TYPE	C-ID											PRESENCE	mandatory	}|
	{ ID	id-ConfigurationGenerationID							CRITICALITY	reject		TYPE	ConfigurationGenerationID						PRESENCE 	mandatory	}|
	{ ID	id-CommonPhysicalChannelType-CTCH-SetupRqstTDD			CRITICALITY	ignore		TYPE 	CommonPhysicalChannelType-CTCH-SetupRqstTDD		PRESENCE 	mandatory	},
	...
}

CommonTransportChannelSetupRequestTDD-Extensions NBAP-PROTOCOL-EXTENSION ::= {
	...
}

CommonPhysicalChannelType-CTCH-SetupRqstTDD ::= CHOICE {
	secondary-CCPCH-parameters					Secondary-CCPCH-CTCH-SetupRqstTDD,
	pRACH-parameters							PRACH-CTCH-SetupRqstTDD,
	...
}

Secondary-CCPCH-CTCH-SetupRqstTDD ::= SEQUENCE {
	sCCPCH-CCTrCH-ID							CCTrCH-ID,
	tFCS										TFCS,
	tFCI-Coding									TFCI-Coding,
	punctureLimit								PunctureLimit,
	secondaryCCPCH-parameterList				Secondary-CCPCH-parameterList-CTCH-SetupRqstTDD,
	fACH-ParametersList							FACH-ParametersList-CTCH-SetupRqstTDD		OPTIONAL,
	pCH-Parameters								PCH-Parameters-CTCH-SetupRqstTDD			OPTIONAL,
	iE-Extensions								ProtocolExtensionContainer	{{Secondary-CCPCHItem-CTCH-SetupRqstTDD-ExtIEs}}		OPTIONAL,
	...
}

Secondary-CCPCHItem-CTCH-SetupRqstTDD-ExtIEs NBAP-PROTOCOL-EXTENSION ::= {
	{ ID	id-Secondary-CCPCH-LCR-parameterList-CTCH-SetupRqstTDD			CRITICALITY	reject		EXTENSION 	Secondary-CCPCH-LCR-parameterList-CTCH-SetupRqstTDD		PRESENCE 	optional	},	-- Mandatory for 1.28Mcps TDD, Not Applicable to 3.84Mcps TDD
	...
}

Secondary-CCPCH-parameterList-CTCH-SetupRqstTDD ::= ProtocolIE-Single-Container {{ Secondary-CCPCH-parameterListIEs-CTCH-SetupRqstTDD }}

Secondary-CCPCH-parameterListIEs-CTCH-SetupRqstTDD NBAP-PROTOCOL-IES ::= {
	{ ID id-Secondary-CCPCH-parameterListIE-CTCH-SetupRqstTDD   CRITICALITY reject	TYPE Secondary-CCPCH-parameterListIE-CTCH-SetupRqstTDD	PRESENCE mandatory }	-- Mandatory for 3.84Mcps TDD, Not Applicable to 1.28Mcps TDD
}

Secondary-CCPCH-parameterListIE-CTCH-SetupRqstTDD ::= SEQUENCE (SIZE (1..maxNrOfSCCPCHs)) OF Secondary-CCPCH-parameterItem-CTCH-SetupRqstTDD

Secondary-CCPCH-parameterItem-CTCH-SetupRqstTDD ::= SEQUENCE {
	commonPhysicalChannelID						CommonPhysicalChannelID,
	tdd-ChannelisationCode						TDD-ChannelisationCode,
	timeslot									TimeSlot,
	midambleShiftandBurstType					MidambleShiftAndBurstType,
	tdd-PhysicalChannelOffset					TDD-PhysicalChannelOffset,
	repetitionPeriod							RepetitionPeriod,
	repetitionLength							RepetitionLength,
	s-CCPCH-Power								DL-Power,
	iE-Extensions								ProtocolExtensionContainer { { Secondary-CCPCH-parameterItem-CTCH-SetupRqstTDD-ExtIEs} }		OPTIONAL,
	...
}

Secondary-CCPCH-parameterItem-CTCH-SetupRqstTDD-ExtIEs NBAP-PROTOCOL-EXTENSION ::= {
	...
}

FACH-ParametersList-CTCH-SetupRqstTDD ::= ProtocolIE-Single-Container {{ FACH-ParametersListIEs-CTCH-SetupRqstTDD }}

FACH-ParametersListIEs-CTCH-SetupRqstTDD NBAP-PROTOCOL-IES ::= {
	{ ID id-FACH-ParametersListIE-CTCH-SetupRqstTDD   CRITICALITY reject	TYPE FACH-ParametersListIE-CTCH-SetupRqstTDD	PRESENCE mandatory }
}

FACH-ParametersListIE-CTCH-SetupRqstTDD ::= SEQUENCE (SIZE (1..maxNrOfFACHs)) OF FACH-ParametersItem-CTCH-SetupRqstTDD

FACH-ParametersItem-CTCH-SetupRqstTDD ::= SEQUENCE {
	commonTransportChannelID				CommonTransportChannelID,
	fACH-CCTrCH-ID							CCTrCH-ID,
	dl-TransportFormatSet					TransportFormatSet,
	toAWS									ToAWS,
	toAWE									ToAWE,
	iE-Extensions							ProtocolExtensionContainer  { { FACH-ParametersItem-CTCH-SetupRqstTDD-ExtIEs} }		OPTIONAL,
	...
}

FACH-ParametersItem-CTCH-SetupRqstTDD-ExtIEs NBAP-PROTOCOL-EXTENSION ::= {
	{ ID	id-maxFACH-Power-LCR-CTCH-SetupRqstTDD			CRITICALITY	reject		EXTENSION 	DL-Power		PRESENCE 	optional	}|
	-- Applicable to 1.28Mcps TDD only
	{ ID	id-bindingID						CRITICALITY	ignore		EXTENSION 	BindingID		PRESENCE 	optional	}|
	{ ID	id-transportlayeraddress			CRITICALITY	ignore		EXTENSION 	TransportLayerAddress		PRESENCE 	optional	},
	...
}

PCH-Parameters-CTCH-SetupRqstTDD ::= ProtocolIE-Single-Container {{ PCH-ParametersIE-CTCH-SetupRqstTDD }}

PCH-ParametersIE-CTCH-SetupRqstTDD NBAP-PROTOCOL-IES ::= {
	{ ID id-PCH-ParametersItem-CTCH-SetupRqstTDD   CRITICALITY reject	TYPE PCH-ParametersItem-CTCH-SetupRqstTDD	PRESENCE mandatory }
}

PCH-ParametersItem-CTCH-SetupRqstTDD ::= SEQUENCE {
	commonTransportChannelID				CommonTransportChannelID,
	pCH-CCTrCH-ID							CCTrCH-ID,
	dl-TransportFormatSet					TransportFormatSet,
	toAWS									ToAWS,
	toAWE									ToAWE,
	pICH-Parameters							PICH-Parameters-CTCH-SetupRqstTDD,
	iE-Extensions							ProtocolExtensionContainer  { { PCH-ParametersItem-CTCH-SetupRqstTDD-ExtIEs} }		OPTIONAL,
	...
}

PCH-ParametersItem-CTCH-SetupRqstTDD-ExtIEs NBAP-PROTOCOL-EXTENSION ::= {
	{ ID	id-PCH-Power-LCR-CTCH-SetupRqstTDD			CRITICALITY	reject		EXTENSION 	DL-Power		PRESENCE 	optional	}|
	-- Applicable to 1.28Mcps TDD only
	{ ID	id-PICH-LCR-Parameters-CTCH-SetupRqstTDD			CRITICALITY	reject		EXTENSION 	PICH-LCR-Parameters-CTCH-SetupRqstTDD		PRESENCE 	optional	}|	-- Mandatory for 1.28Mcps TDD, Not Applicable to 3.84Mcps TDD
	{ ID	id-bindingID						CRITICALITY	ignore		EXTENSION 	BindingID		PRESENCE 	optional	}|
	{ ID	id-transportlayeraddress			CRITICALITY	ignore		EXTENSION 	TransportLayerAddress		PRESENCE 	optional	},
	...
}

PICH-Parameters-CTCH-SetupRqstTDD ::= ProtocolIE-Single-Container {{ PICH-ParametersIE-CTCH-SetupRqstTDD }}

PICH-ParametersIE-CTCH-SetupRqstTDD NBAP-PROTOCOL-IES ::= {
	{ ID id-PICH-ParametersItem-CTCH-SetupRqstTDD   CRITICALITY reject	TYPE PICH-ParametersItem-CTCH-SetupRqstTDD	PRESENCE optional }
}	-- Mandatory for 3.84Mcps TDD, Not Applicable to 1.28Mcps TDD

PICH-ParametersItem-CTCH-SetupRqstTDD ::= SEQUENCE {
	commonPhysicalChannelID					CommonPhysicalChannelID,
 	tdd-ChannelisationCode					TDD-ChannelisationCode,
 	timeSlot  								TimeSlot,
	midambleshiftAndBurstType				MidambleShiftAndBurstType,
 	tdd-PhysicalChannelOffset				TDD-PhysicalChannelOffset,
 	repetitionPeriod						RepetitionPeriod,
 	repetitionLength						RepetitionLength,
 	pagingIndicatorLength					PagingIndicatorLength,
	pICH-Power								PICH-Power,
	iE-Extensions							ProtocolExtensionContainer  { { PICH-ParametersItem-CTCH-SetupRqstTDD-ExtIEs} }		OPTIONAL,
	...
}

PICH-ParametersItem-CTCH-SetupRqstTDD-ExtIEs NBAP-PROTOCOL-EXTENSION ::= {
	...
}

PICH-LCR-Parameters-CTCH-SetupRqstTDD ::= SEQUENCE {
	commonPhysicalChannelID					CommonPhysicalChannelID,
 	tdd-ChannelisationCodeLCR				TDD-ChannelisationCodeLCR,
 	timeSlotLCR  							TimeSlotLCR,
	midambleShiftLCR						MidambleShiftLCR,
	tdd-PhysicalChannelOffset				TDD-PhysicalChannelOffset,
 	repetitionPeriod						RepetitionPeriod,
 	repetitionLength						RepetitionLength,
 	pagingIndicatorLength					PagingIndicatorLength,
	pICH-Power								PICH-Power,
	second-TDD-ChannelisationCodeLCR		TDD-ChannelisationCodeLCR,
	iE-Extensions							ProtocolExtensionContainer  { { PICH-LCR-ParametersItem-CTCH-SetupRqstTDD-ExtIEs} }		OPTIONAL,
	...
}

PICH-LCR-ParametersItem-CTCH-SetupRqstTDD-ExtIEs NBAP-PROTOCOL-EXTENSION ::= {
	...
}

Secondary-CCPCH-LCR-parameterList-CTCH-SetupRqstTDD ::= SEQUENCE (SIZE (1..maxNrOfSCCPCHLCRs)) OF Secondary-CCPCH-LCR-parameterItem-CTCH-SetupRqstTDD

Secondary-CCPCH-LCR-parameterItem-CTCH-SetupRqstTDD ::= SEQUENCE {
	commonPhysicalChannelID						CommonPhysicalChannelID,
	tdd-ChannelisationCodeLCR					TDD-ChannelisationCodeLCR,
	timeslotLCR									TimeSlotLCR,
	midambleShiftLCR							MidambleShiftLCR,
	tdd-PhysicalChannelOffset					TDD-PhysicalChannelOffset,
	repetitionPeriod							RepetitionPeriod,
	repetitionLength							RepetitionLength,
	s-CCPCH-Power								DL-Power,
	s-CCPCH-TimeSlotFormat-LCR					TDD-DL-DPCH-TimeSlotFormat-LCR,
	iE-Extensions								ProtocolExtensionContainer { { Secondary-CCPCH-LCR-parameterItem-CTCH-SetupRqstTDD-ExtIEs} }		OPTIONAL,
	...
}

Secondary-CCPCH-LCR-parameterItem-CTCH-SetupRqstTDD-ExtIEs NBAP-PROTOCOL-EXTENSION ::= {
	...
}

PRACH-CTCH-SetupRqstTDD ::= SEQUENCE {
	pRACH-Parameters-CTCH-SetupRqstTDD			PRACH-Parameters-CTCH-SetupRqstTDD,
	iE-Extensions								ProtocolExtensionContainer  { { PRACH-CTCH-SetupRqstTDD-ExtIEs } }		OPTIONAL,
	...
}

PRACH-CTCH-SetupRqstTDD-ExtIEs NBAP-PROTOCOL-EXTENSION ::= {
	{ ID	id-PRACH-LCR-ParametersList-CTCH-SetupRqstTDD			CRITICALITY	reject		EXTENSION	PRACH-LCR-ParametersList-CTCH-SetupRqstTDD		PRESENCE 	optional	}|	-- Mandatory for 1.28Mcps TDD, Not Applicable to 3.84Mcps TDD
	{ ID	id-FPACH-LCR-Parameters-CTCH-SetupRqstTDD			CRITICALITY	reject		EXTENSION 	FPACH-LCR-Parameters-CTCH-SetupRqstTDD		PRESENCE 	optional	},	-- Mandatory for 1.28Mcps TDD, Not Applicable to 3.84Mcps TDD
	...
}

PRACH-Parameters-CTCH-SetupRqstTDD ::= ProtocolIE-Single-Container {{ PRACH-ParametersIE-CTCH-SetupRqstTDD }}

PRACH-ParametersIE-CTCH-SetupRqstTDD NBAP-PROTOCOL-IES ::= {
	{ ID id-PRACH-ParametersItem-CTCH-SetupRqstTDD   CRITICALITY reject	TYPE PRACH-ParametersItem-CTCH-SetupRqstTDD	PRESENCE optional }
}	-- Mandatory for 3.84Mcps TDD, Not Applicable to 1.28Mcps TDD


PRACH-ParametersItem-CTCH-SetupRqstTDD ::= SEQUENCE {
	commonPhysicalChannelID						CommonPhysicalChannelID,
	tFCS										TFCS,
	timeslot									TimeSlot,
	tdd-ChannelisationCode						TDD-ChannelisationCode,
	maxPRACH-MidambleShifts						MaxPRACH-MidambleShifts,
	pRACH-Midamble 								PRACH-Midamble,
	rACH										RACH-Parameter-CTCH-SetupRqstTDD,
	iE-Extensions								ProtocolExtensionContainer  { { PRACH-ParametersItem-CTCH-SetupRqstTDD-ExtIEs} }		OPTIONAL,
	...
}

PRACH-ParametersItem-CTCH-SetupRqstTDD-ExtIEs NBAP-PROTOCOL-EXTENSION ::= {
	...
}

RACH-Parameter-CTCH-SetupRqstTDD ::= ProtocolIE-Single-Container {{ RACH-ParameterIE-CTCH-SetupRqstTDD }}

RACH-ParameterIE-CTCH-SetupRqstTDD NBAP-PROTOCOL-IES ::= {
	{ ID id-RACH-ParameterItem-CTCH-SetupRqstTDD   CRITICALITY reject	TYPE RACH-ParameterItem-CTCH-SetupRqstTDD	PRESENCE mandatory }
}

RACH-ParameterItem-CTCH-SetupRqstTDD ::= SEQUENCE {
	commonTransportChannelID					CommonTransportChannelID,
	uL-TransportFormatSet						TransportFormatSet,
	iE-Extensions								ProtocolExtensionContainer  { { RACH-ParameterItem-CTCH-SetupRqstTDD-ExtIEs} }		OPTIONAL,
	...
}

RACH-ParameterItem-CTCH-SetupRqstTDD-ExtIEs NBAP-PROTOCOL-EXTENSION ::= {
	{ ID	id-bindingID						CRITICALITY	ignore		EXTENSION 	BindingID		PRESENCE 	optional	}|
	{ ID	id-transportlayeraddress			CRITICALITY	ignore		EXTENSION 	TransportLayerAddress		PRESENCE 	optional	},
	...
}

PRACH-LCR-ParametersList-CTCH-SetupRqstTDD ::= SEQUENCE (SIZE (1..maxNrOfPRACHLCRs)) OF PRACH-LCR-ParametersItem-CTCH-SetupRqstTDD 

PRACH-LCR-ParametersItem-CTCH-SetupRqstTDD ::= SEQUENCE {
	commonPhysicalChannelID						CommonPhysicalChannelID,
	tFCS										TFCS,
	timeslotLCR									TimeSlotLCR,
	tdd-ChannelisationCodeLCR					TDD-ChannelisationCodeLCR,
	maxPRACH-MidambleShifts						MaxPRACH-MidambleShifts,
	pRACH-Midamble 								PRACH-Midamble,
	rACH										RACH-Parameter-CTCH-SetupRqstTDD,
	iE-Extensions								ProtocolExtensionContainer  { { PRACH-LCR-ParametersItem-CTCH-SetupRqstTDD-ExtIEs} }		OPTIONAL,
	...
}

PRACH-LCR-ParametersItem-CTCH-SetupRqstTDD-ExtIEs NBAP-PROTOCOL-EXTENSION ::= {
	...
}

FPACH-LCR-Parameters-CTCH-SetupRqstTDD ::= SEQUENCE {
	commonPhysicalChannelID						CommonPhysicalChannelID,
 	tdd-ChannelisationCodeLCR					TDD-ChannelisationCodeLCR,
	timeslotLCR									TimeSlotLCR,
	midambleShiftLCR							MidambleShiftLCR,
	fPACH-Power								FPACH-Power,
	iE-Extensions								ProtocolExtensionContainer  { { FPACH-LCR-ParametersItem-CTCH-SetupRqstTDD-ExtIEs} }		OPTIONAL,
	...
}

FPACH-LCR-ParametersItem-CTCH-SetupRqstTDD-ExtIEs NBAP-PROTOCOL-EXTENSION ::= {
	...
}

-- **************************************************************
--
-- COMMON TRANSPORT CHANNEL SETUP RESPONSE
--
-- **************************************************************

CommonTransportChannelSetupResponse ::= SEQUENCE {
	protocolIEs				ProtocolIE-Container	{{CommonTransportChannelSetupResponse-IEs}},
	protocolExtensions		ProtocolExtensionContainer	{{CommonTransportChannelSetupResponse-Extensions}}    OPTIONAL,
	...
}

CommonTransportChannelSetupResponse-IEs NBAP-PROTOCOL-IES ::= {
	{ ID	id-FACH-ParametersList-CTCH-SetupRsp	CRITICALITY	ignore		TYPE	FACH-CommonTransportChannel-InformationResponse		PRESENCE	optional	}|
	{ ID	id-PCH-Parameters-CTCH-SetupRsp			CRITICALITY	ignore		TYPE	CommonTransportChannel-InformationResponse				PRESENCE	optional	}|
	{ ID	id-RACH-Parameters-CTCH-SetupRsp		CRITICALITY	ignore		TYPE	CommonTransportChannel-InformationResponse			PRESENCE	optional	}|
	{ ID	id-CPCH-Parameters-CTCH-SetupRsp		CRITICALITY	ignore				TYPE	CommonTransportChannel-InformationResponse			PRESENCE	optional	}|
	{ ID	id-CriticalityDiagnostics						CRITICALITY		ignore		TYPE	CriticalityDiagnostics							PRESENCE	optional	},
	...
}

CommonTransportChannelSetupResponse-Extensions NBAP-PROTOCOL-EXTENSION ::= {
	...
}

FACH-CommonTransportChannel-InformationResponse ::= SEQUENCE (SIZE (1..maxNrOfFACHs)) OF CommonTransportChannel-InformationResponse

-- **************************************************************
--
-- COMMON TRANSPORT CHANNEL SETUP FAILURE
--
-- **************************************************************

CommonTransportChannelSetupFailure ::= SEQUENCE {
	protocolIEs				ProtocolIE-Container	{{CommonTransportChannelSetupFailure-IEs}},
	protocolExtensions		ProtocolExtensionContainer	{{CommonTransportChannelSetupFailure-Extensions}}     OPTIONAL,
	...
}

CommonTransportChannelSetupFailure-IEs NBAP-PROTOCOL-IES ::= {
	{ ID	id-Cause					CRITICALITY	ignore		TYPE	Cause						PRESENCE	mandatory	}|
	{ ID	id-CriticalityDiagnostics	CRITICALITY	ignore		TYPE	CriticalityDiagnostics		PRESENCE	optional		},
	...
}

CommonTransportChannelSetupFailure-Extensions NBAP-PROTOCOL-EXTENSION ::= {
	...
}

-- **************************************************************
--
-- COMMON TRANSPORT CHANNEL RECONFIGURATION REQUEST FDD
--
-- **************************************************************

CommonTransportChannelReconfigurationRequestFDD ::= SEQUENCE {
	protocolIEs				ProtocolIE-Container	{{CommonTransportChannelReconfigurationRequestFDD-IEs}},
	protocolExtensions		ProtocolExtensionContainer	{{CommonTransportChannelReconfigurationRequestFDD-Extensions}}		OPTIONAL,
	...
}

CommonTransportChannelReconfigurationRequestFDD-IEs NBAP-PROTOCOL-IES ::= {
	{ ID	id-C-ID										CRITICALITY	reject		TYPE	C-ID											PRESENCE mandatory	}|
	{ ID	id-ConfigurationGenerationID				CRITICALITY	reject		TYPE	ConfigurationGenerationID				PRESENCE	mandatory	}|
	{ ID	id-CommonPhysicalChannelType-CTCH-ReconfRqstFDD	CRITICALITY	reject	TYPE	CommonPhysicalChannelType-CTCH-ReconfRqstFDD	PRESENCE	mandatory	},
	...
}

CommonTransportChannelReconfigurationRequestFDD-Extensions NBAP-PROTOCOL-EXTENSION ::= {
	...
}

CommonPhysicalChannelType-CTCH-ReconfRqstFDD ::= CHOICE {
	secondary-CCPCH-parameters		Secondary-CCPCHList-CTCH-ReconfRqstFDD,
	pRACH-parameters				PRACHList-CTCH-ReconfRqstFDD,
	cPCH-parameters					CPCHList-CTCH-ReconfRqstFDD,
	...
}

Secondary-CCPCHList-CTCH-ReconfRqstFDD ::= SEQUENCE {
	fACH-ParametersList-CTCH-ReconfRqstFDD		FACH-ParametersList-CTCH-ReconfRqstFDD	OPTIONAL,
	pCH-Parameters-CTCH-ReconfRqstFDD			PCH-Parameters-CTCH-ReconfRqstFDD		OPTIONAL,
	pICH-Parameters-CTCH-ReconfRqstFDD			PICH-Parameters-CTCH-ReconfRqstFDD		OPTIONAL,
	iE-Extensions								ProtocolExtensionContainer { { Secondary-CCPCH-CTCH-ReconfRqstFDD-ExtIEs} } OPTIONAL,
	...
}

Secondary-CCPCH-CTCH-ReconfRqstFDD-ExtIEs NBAP-PROTOCOL-EXTENSION ::= {
	...
}

FACH-ParametersList-CTCH-ReconfRqstFDD ::= ProtocolIE-Single-Container {{ FACH-ParametersListIEs-CTCH-ReconfRqstFDD }}

FACH-ParametersListIEs-CTCH-ReconfRqstFDD NBAP-PROTOCOL-IES ::= {
	{ ID id-FACH-ParametersListIE-CTCH-ReconfRqstFDD	CRITICALITY reject	TYPE FACH-ParametersListIE-CTCH-ReconfRqstFDD 	PRESENCE	mandatory }
}

FACH-ParametersListIE-CTCH-ReconfRqstFDD ::= SEQUENCE (SIZE (1..maxFACHCell)) OF FACH-ParametersItem-CTCH-ReconfRqstFDD

FACH-ParametersItem-CTCH-ReconfRqstFDD ::= SEQUENCE {
	commonTransportChannelID				CommonTransportChannelID,
	maxFACH-Power							DL-Power		OPTIONAL,
	toAWS									ToAWS			OPTIONAL,
	toAWE									ToAWE			OPTIONAL,
	iE-Extensions							ProtocolExtensionContainer  { { FACH-ParametersItem-CTCH-ReconfRqstFDD-ExtIEs} }		OPTIONAL,
	...
}

FACH-ParametersItem-CTCH-ReconfRqstFDD-ExtIEs NBAP-PROTOCOL-EXTENSION ::= {
	...
}

PCH-Parameters-CTCH-ReconfRqstFDD ::= ProtocolIE-Single-Container {{ PCH-ParametersIE-CTCH-ReconfRqstFDD }}

PCH-ParametersIE-CTCH-ReconfRqstFDD NBAP-PROTOCOL-IES ::= {
	{ ID id-PCH-ParametersItem-CTCH-ReconfRqstFDD	CRITICALITY reject	TYPE PCH-ParametersItem-CTCH-ReconfRqstFDD 	PRESENCE	mandatory }
}

PCH-ParametersItem-CTCH-ReconfRqstFDD ::= SEQUENCE {
	commonTransportChannelID				CommonTransportChannelID,
	pCH-Power								DL-Power		OPTIONAL,
	toAWS									ToAWS			OPTIONAL,
	toAWE									ToAWE			OPTIONAL,
	iE-Extensions							ProtocolExtensionContainer  { { PCH-ParametersItem-CTCH-ReconfRqstFDD-ExtIEs} }			OPTIONAL,
	...
}

PCH-ParametersItem-CTCH-ReconfRqstFDD-ExtIEs NBAP-PROTOCOL-EXTENSION ::= {
	...
}

PICH-Parameters-CTCH-ReconfRqstFDD ::= ProtocolIE-Single-Container {{ PICH-ParametersIE-CTCH-ReconfRqstFDD }}

PICH-ParametersIE-CTCH-ReconfRqstFDD NBAP-PROTOCOL-IES ::= {
	{ ID id-PICH-ParametersItem-CTCH-ReconfRqstFDD	CRITICALITY reject	TYPE PICH-ParametersItem-CTCH-ReconfRqstFDD 	PRESENCE	mandatory }
}

PICH-ParametersItem-CTCH-ReconfRqstFDD ::= SEQUENCE {
	commonPhysicalChannelID				CommonPhysicalChannelID,
	pICH-Power								PICH-Power		OPTIONAL,
	iE-Extensions							ProtocolExtensionContainer  { { PICH-ParametersItem-CTCH-ReconfRqstFDD-ExtIEs} }		OPTIONAL,
	...
}

PICH-ParametersItem-CTCH-ReconfRqstFDD-ExtIEs NBAP-PROTOCOL-EXTENSION ::= {
	...
}

PRACHList-CTCH-ReconfRqstFDD ::= SEQUENCE {
	pRACH-ParametersList-CTCH-ReconfRqstFDD		PRACH-ParametersList-CTCH-ReconfRqstFDD	OPTIONAL,
	aICH-ParametersList-CTCH-ReconfRqstFDD		AICH-ParametersList-CTCH-ReconfRqstFDD	OPTIONAL,
	iE-Extensions								ProtocolExtensionContainer { { PRACH-CTCH-ReconfRqstFDD-ExtIEs} } OPTIONAL,
	...
}

PRACH-CTCH-ReconfRqstFDD-ExtIEs NBAP-PROTOCOL-EXTENSION ::= {
	...
}

PRACH-ParametersList-CTCH-ReconfRqstFDD ::= ProtocolIE-Single-Container {{ PRACH-ParametersListIEs-CTCH-ReconfRqstFDD }}

PRACH-ParametersListIEs-CTCH-ReconfRqstFDD NBAP-PROTOCOL-IES ::= {
	{ ID id-PRACH-ParametersListIE-CTCH-ReconfRqstFDD	CRITICALITY reject	TYPE PRACH-ParametersListIE-CTCH-ReconfRqstFDD 	PRESENCE	mandatory }
}

PRACH-ParametersListIE-CTCH-ReconfRqstFDD ::= SEQUENCE (SIZE (1..maxPRACHCell)) OF PRACH-ParametersItem-CTCH-ReconfRqstFDD

PRACH-ParametersItem-CTCH-ReconfRqstFDD ::= SEQUENCE {
	commonPhysicalChannelID				CommonPhysicalChannelID,
	preambleSignatures						PreambleSignatures		OPTIONAL,
	allowedSlotFormatInformation			AllowedSlotFormatInformationList-CTCH-ReconfRqstFDD		OPTIONAL,
	rACH-SubChannelNumbers					RACH-SubChannelNumbers		OPTIONAL,
	iE-Extensions							ProtocolExtensionContainer  { { PRACH-ParametersItem-CTCH-ReconfRqstFDD-ExtIEs} }		OPTIONAL,
	...
}

PRACH-ParametersItem-CTCH-ReconfRqstFDD-ExtIEs NBAP-PROTOCOL-EXTENSION ::= {
	...
}

AllowedSlotFormatInformationList-CTCH-ReconfRqstFDD ::= SEQUENCE (SIZE (1.. maxNrOfSlotFormatsPRACH)) OF AllowedSlotFormatInformationItem-CTCH-ReconfRqstFDD

AllowedSlotFormatInformationItem-CTCH-ReconfRqstFDD ::= SEQUENCE {
	rACH-SlotFormat							RACH-SlotFormat,
	iE-Extensions							ProtocolExtensionContainer  { { AllowedSlotFormatInformationItem-CTCH-ReconfRqstFDD-ExtIEs} }		OPTIONAL,
	...
}

AllowedSlotFormatInformationItem-CTCH-ReconfRqstFDD-ExtIEs NBAP-PROTOCOL-EXTENSION ::= {
	...
}

AICH-ParametersList-CTCH-ReconfRqstFDD ::= ProtocolIE-Single-Container {{ AICH-ParametersListIEs-CTCH-ReconfRqstFDD }}

AICH-ParametersListIEs-CTCH-ReconfRqstFDD NBAP-PROTOCOL-IES ::= {
	{ ID id-AICH-ParametersListIE-CTCH-ReconfRqstFDD	CRITICALITY reject	TYPE AICH-ParametersListIE-CTCH-ReconfRqstFDD 	PRESENCE	mandatory }
}

AICH-ParametersListIE-CTCH-ReconfRqstFDD ::= SEQUENCE (SIZE (1..maxPRACHCell)) OF AICH-ParametersItem-CTCH-ReconfRqstFDD

AICH-ParametersItem-CTCH-ReconfRqstFDD ::= SEQUENCE {
	commonPhysicalChannelID				CommonPhysicalChannelID,
	aICH-Power								AICH-Power		OPTIONAL,
	iE-Extensions							ProtocolExtensionContainer  { { AICH-ParametersItemIE-CTCH-ReconfRqstFDD-ExtIEs} }		OPTIONAL,
	...
}

AICH-ParametersItemIE-CTCH-ReconfRqstFDD-ExtIEs NBAP-PROTOCOL-EXTENSION ::= {
	...
}

CPCHList-CTCH-ReconfRqstFDD ::= SEQUENCE {
	cPCH-ParametersList-CTCH-ReconfRqstFDD			CPCH-ParametersList-CTCH-ReconfRqstFDD					OPTIONAL,
	aP-AICH-ParametersList-CTCH-ReconfRqstFDD		AP-AICH-ParametersList-CTCH-ReconfRqstFDD		OPTIONAL,
	cDCA-ICH-ParametersList-CTCH-ReconfRqstFDD		CDCA-ICH-ParametersList-CTCH-ReconfRqstFDD		OPTIONAL,
	iE-Extensions									ProtocolExtensionContainer  { { CPCHListItem-CTCH-ReconfRqstFDD-ExtIEs} }		OPTIONAL,
	...
}

CPCHListItem-CTCH-ReconfRqstFDD-ExtIEs NBAP-PROTOCOL-EXTENSION ::= {
	...
}

CPCH-ParametersList-CTCH-ReconfRqstFDD ::= ProtocolIE-Single-Container {{ CPCH-ParametersListIEs-CTCH-ReconfRqstFDD }}

CPCH-ParametersListIEs-CTCH-ReconfRqstFDD NBAP-PROTOCOL-IES ::= {
	{ ID id-CPCH-ParametersListIE-CTCH-ReconfRqstFDD	CRITICALITY reject	TYPE CPCH-ParametersListIE-CTCH-ReconfRqstFDD 	PRESENCE	mandatory }
}

CPCH-ParametersListIE-CTCH-ReconfRqstFDD ::= SEQUENCE (SIZE (1..maxNrOfCPCHs)) OF CPCH-ParametersItem-CTCH-ReconfRqstFDD

CPCH-ParametersItem-CTCH-ReconfRqstFDD ::= SEQUENCE {
	commonTransportChannelID		CommonTransportChannelID,
	uL-SIR							UL-SIR			OPTIONAL,
	initialDL-transmissionPower		DL-Power		OPTIONAL,
   maximumDLPower					DL-Power		OPTIONAL,
    minimumDLPower					DL-Power		OPTIONAL,
	iE-Extensions					ProtocolExtensionContainer  { { CPCH-ParametersItem-CTCH-ReconfRqstFDD-ExtIEs} }		OPTIONAL,
	...
}

CPCH-ParametersItem-CTCH-ReconfRqstFDD-ExtIEs NBAP-PROTOCOL-EXTENSION ::= {
	...
}

AP-AICH-ParametersList-CTCH-ReconfRqstFDD ::= ProtocolIE-Single-Container {{ AP-AICH-ParametersListIEs-CTCH-ReconfRqstFDD }}

AP-AICH-ParametersListIEs-CTCH-ReconfRqstFDD NBAP-PROTOCOL-IES ::= {
	{ ID id-AP-AICH-ParametersListIE-CTCH-ReconfRqstFDD	CRITICALITY reject	TYPE AP-AICH-ParametersListIE-CTCH-ReconfRqstFDD 	PRESENCE	mandatory }
}

AP-AICH-ParametersListIE-CTCH-ReconfRqstFDD ::= SEQUENCE (SIZE (1..maxNrOfCPCHs)) OF AP-AICH-ParametersItem-CTCH-ReconfRqstFDD

AP-AICH-ParametersItem-CTCH-ReconfRqstFDD ::= SEQUENCE {
	commonPhysicalChannelID				CommonPhysicalChannelID,
	aP-AICH-Power							AICH-Power		OPTIONAL,
	cSICH-Power								AICH-Power		OPTIONAL,
	iE-Extensions							ProtocolExtensionContainer  { { AP-AICH-ParametersItemIE-CTCH-ReconfRqstFDD-ExtIEs} }		OPTIONAL,
	...
}

AP-AICH-ParametersItemIE-CTCH-ReconfRqstFDD-ExtIEs NBAP-PROTOCOL-EXTENSION ::= {
	...
}

CDCA-ICH-ParametersList-CTCH-ReconfRqstFDD ::= ProtocolIE-Single-Container {{ CDCA-ICH-ParametersListIEs-CTCH-ReconfRqstFDD }}

CDCA-ICH-ParametersListIEs-CTCH-ReconfRqstFDD NBAP-PROTOCOL-IES ::= {
	{ ID id-CDCA-ICH-ParametersListIE-CTCH-ReconfRqstFDD	CRITICALITY reject	TYPE CDCA-ICH-ParametersListIE-CTCH-ReconfRqstFDD 	PRESENCE	mandatory }
}

CDCA-ICH-ParametersListIE-CTCH-ReconfRqstFDD ::= SEQUENCE (SIZE (1..maxNrOfCPCHs)) OF CDCA-ICH-ParametersItem-CTCH-ReconfRqstFDD

CDCA-ICH-ParametersItem-CTCH-ReconfRqstFDD ::= SEQUENCE {
	commonPhysicalChannelID				CommonPhysicalChannelID,
	cDCA-ICH-Power							AICH-Power		OPTIONAL,
	iE-Extensions							ProtocolExtensionContainer  { { CDCA-ICH-ParametersItemIE-CTCH-ReconfRqstFDD-ExtIEs} }		OPTIONAL,
	...
}

CDCA-ICH-ParametersItemIE-CTCH-ReconfRqstFDD-ExtIEs NBAP-PROTOCOL-EXTENSION ::= {
	...
}

-- **************************************************************
--
-- COMMON TRANSPORT CHANNEL RECONFIGURATION REQUEST TDD
--
-- **************************************************************

CommonTransportChannelReconfigurationRequestTDD ::= SEQUENCE {
	protocolIEs				ProtocolIE-Container	{{CommonTransportChannelReconfigurationRequestTDD-IEs}},
	protocolExtensions		ProtocolExtensionContainer	{{CommonTransportChannelReconfigurationRequestTDD-Extensions}}		OPTIONAL,
	...
}

CommonTransportChannelReconfigurationRequestTDD-IEs NBAP-PROTOCOL-IES ::= {
	{ ID	id-C-ID												CRITICALITY	reject		TYPE	C-ID											PRESENCE 	mandatory	}|
	{ ID 	id-ConfigurationGenerationID						CRITICALITY	reject		TYPE	ConfigurationGenerationID						PRESENCE	mandatory	}|
	{ ID id-Secondary-CCPCH-Parameters-CTCH-ReconfRqstTDD			CRITICALITY reject	TYPE	 Secondary-CCPCH-Parameters-CTCH-ReconfRqstTDD			PRESENCE optional	}|
	{ ID id-PICH-Parameters-CTCH-ReconfRqstTDD		CRITICALITY reject	TYPE 	PICH-Parameters-CTCH-ReconfRqstTDD			PRESENCE optional	}|
	{ ID id-FACH-ParametersList-CTCH-ReconfRqstTDD	CRITICALITY reject	TYPE  FACH-ParametersList-CTCH-ReconfRqstTDD	PRESENCE optional	}|
	{ ID id-PCH-Parameters-CTCH-ReconfRqstTDD		CRITICALITY reject	TYPE 	PCH-Parameters-CTCH-ReconfRqstTDD			PRESENCE optional	},
	...
}

CommonTransportChannelReconfigurationRequestTDD-Extensions NBAP-PROTOCOL-EXTENSION ::= {
	{ ID id-FPACH-LCR-Parameters-CTCH-ReconfRqstTDD		CRITICALITY reject	EXTENSION 	FPACH-LCR-Parameters-CTCH-ReconfRqstTDD			PRESENCE optional	},	-- Mandatory For 1.28Mcps TDD, Not Applicable to 3.84Mcps TDD
	...
}

Secondary-CCPCH-Parameters-CTCH-ReconfRqstTDD::= SEQUENCE {
	cCTrCH-ID						CCTrCH-ID,
	secondaryCCPCHList				Secondary-CCPCHList-CTCH-ReconfRqstTDD			OPTIONAL,
	iE-Extensions					ProtocolExtensionContainer  { { Secondary-CCPCH-CTCH-ReconfRqstTDD-ExtIEs} }		OPTIONAL,
	...
}

Secondary-CCPCH-CTCH-ReconfRqstTDD-ExtIEs NBAP-PROTOCOL-EXTENSION ::= {
	...
}

Secondary-CCPCHList-CTCH-ReconfRqstTDD ::= ProtocolIE-Single-Container {{ Secondary-CCPCHListIEs-CTCH-ReconfRqstTDD }}

Secondary-CCPCHListIEs-CTCH-ReconfRqstTDD NBAP-PROTOCOL-IES ::= {
	{ ID id-Secondary-CCPCHListIE-CTCH-ReconfRqstTDD	CRITICALITY reject	TYPE Secondary-CCPCHListIE-CTCH-ReconfRqstTDD 	PRESENCE	mandatory }
}

Secondary-CCPCHListIE-CTCH-ReconfRqstTDD ::= SEQUENCE (SIZE (1..maxNrOfSCCPCHs)) OF Secondary-CCPCHItem-CTCH-ReconfRqstTDD

Secondary-CCPCHItem-CTCH-ReconfRqstTDD ::= SEQUENCE {
	commonPhysicalChannelID				CommonPhysicalChannelID,
	sCCPCH-Power						DL-Power		OPTIONAL,
	iE-Extensions						ProtocolExtensionContainer  { { Secondary-CCPCHItem-CTCH-ReconfRqstTDD-ExtIEs} }		OPTIONAL,
	...
}

Secondary-CCPCHItem-CTCH-ReconfRqstTDD-ExtIEs NBAP-PROTOCOL-EXTENSION ::= {
	...
}

PICH-Parameters-CTCH-ReconfRqstTDD	 ::= SEQUENCE {
	commonPhysicalChannelID				CommonPhysicalChannelID,
	pICH-Power							PICH-Power		OPTIONAL,
	iE-Extensions						ProtocolExtensionContainer  { { PICH-Parameters-CTCH-ReconfRqstTDD-ExtIEs} }		OPTIONAL,
	...
}

PICH-Parameters-CTCH-ReconfRqstTDD-ExtIEs NBAP-PROTOCOL-EXTENSION ::= {
	...
}

FACH-ParametersList-CTCH-ReconfRqstTDD ::= SEQUENCE (SIZE (0..maxNrOfFACHs)) OF FACH-ParametersItem-CTCH-ReconfRqstTDD

FACH-ParametersItem-CTCH-ReconfRqstTDD ::= SEQUENCE {
 	commonTransportChannelID		CommonTransportChannelID,
	toAWS							ToAWS			OPTIONAL,
 	toAWE							ToAWE			OPTIONAL,
	iE-Extensions					ProtocolExtensionContainer  { { FACH-ParametersItem-CTCH-ReconfRqstTDD-ExtIEs} }		OPTIONAL,
	...
}

FACH-ParametersItem-CTCH-ReconfRqstTDD-ExtIEs NBAP-PROTOCOL-EXTENSION ::= {
	{ ID	id-maxFACH-Power-LCR-CTCH-ReconfRqstTDD			CRITICALITY	reject		EXTENSION 	DL-Power		PRESENCE 	optional	},
	--  Applicable to 1.28Mcps TDD only
	...
}

PCH-Parameters-CTCH-ReconfRqstTDD ::= SEQUENCE {
	commonTransportChannelID		CommonTransportChannelID,
	toAWS							ToAWS			OPTIONAL,
	toAWE							ToAWE			OPTIONAL,
	iE-Extensions					ProtocolExtensionContainer  { { PCH-Parameters-CTCH-ReconfRqstTDD-ExtIEs} }		OPTIONAL,
	...
}

PCH-Parameters-CTCH-ReconfRqstTDD-ExtIEs NBAP-PROTOCOL-EXTENSION ::= {
	{ ID	id-PCH-Power-LCR-CTCH-ReconfRqstTDD			CRITICALITY	reject		EXTENSION 	DL-Power		PRESENCE 	optional	},
	...	-- Applicable to 1.28Mcps TDD only
}

FPACH-LCR-Parameters-CTCH-ReconfRqstTDD ::= SEQUENCE {
	commonPhysicalChannelId			CommonPhysicalChannelID,
	fPACHPower					FPACH-Power		OPTIONAL,
	iE-Extensions					ProtocolExtensionContainer  { { FPACH-LCR-Parameters-CTCH-ReconfRqstTDD-ExtIEs} }		OPTIONAL,
	...
}

FPACH-LCR-Parameters-CTCH-ReconfRqstTDD-ExtIEs NBAP-PROTOCOL-EXTENSION ::= {
	...
}

-- **************************************************************
--
-- COMMON TRANSPORT CHANNEL RECONFIGURATION RESPONSE
--
-- **************************************************************

CommonTransportChannelReconfigurationResponse ::= SEQUENCE {
	protocolIEs				ProtocolIE-Container	{{CommonTransportChannelReconfigurationResponse-IEs}},
	protocolExtensions		ProtocolExtensionContainer	{{CommonTransportChannelReconfigurationResponse-Extensions}}		OPTIONAL,
	...
}

CommonTransportChannelReconfigurationResponse-IEs NBAP-PROTOCOL-IES ::= {	
	{ ID	id-CriticalityDiagnostics		CRITICALITY		ignore			TYPE	CriticalityDiagnostics		PRESENCE	optional},
	...
}

CommonTransportChannelReconfigurationResponse-Extensions NBAP-PROTOCOL-EXTENSION ::= {
	...
}

-- **************************************************************
--
-- COMMON TRANSPORT CHANNEL RECONFIGURATION FAILURE
--
-- **************************************************************

CommonTransportChannelReconfigurationFailure ::= SEQUENCE {
	protocolIEs				ProtocolIE-Container	{{CommonTransportChannelReconfigurationFailure-IEs}},
	protocolExtensions		ProtocolExtensionContainer	{{CommonTransportChannelReconfigurationFailure-Extensions}}          OPTIONAL,
	...
}

CommonTransportChannelReconfigurationFailure-IEs NBAP-PROTOCOL-IES ::= {
	{ ID	id-Cause						CRITICALITY	ignore			TYPE	Cause						PRESENCE	mandatory	}|
	{ ID	id-CriticalityDiagnostics		CRITICALITY	ignore			TYPE	CriticalityDiagnostics		PRESENCE	optional	},
	...
}

CommonTransportChannelReconfigurationFailure-Extensions NBAP-PROTOCOL-EXTENSION ::= {
	...
}

-- **************************************************************
--
-- COMMON TRANSPORT CHANNEL DELETION REQUEST
--
-- **************************************************************

CommonTransportChannelDeletionRequest ::= SEQUENCE {
	protocolIEs					ProtocolIE-Container	{{CommonTransportChannelDeletionRequest-IEs}},
	protocolExtensions			ProtocolExtensionContainer	{{CommonTransportChannelDeletionRequest-Extensions}}        	OPTIONAL,
	...
}

CommonTransportChannelDeletionRequest-IEs NBAP-PROTOCOL-IES ::= {
	{ ID	id-C-ID								CRITICALITY	reject		TYPE	C-ID						PRESENCE 	mandatory}|
	{ ID	id-CommonPhysicalChannelID			CRITICALITY	reject		TYPE	CommonPhysicalChannelID		PRESENCE	mandatory}|
	{ ID	id-ConfigurationGenerationID		CRITICALITY	reject		TYPE	ConfigurationGenerationID	PRESENCE	mandatory},
	...
}

CommonTransportChannelDeletionRequest-Extensions NBAP-PROTOCOL-EXTENSION ::= {
	...
}

-- **************************************************************
--
-- COMMON TRANSPORT CHANNEL DELETION RESPONSE
--
-- **************************************************************

CommonTransportChannelDeletionResponse ::= SEQUENCE {
	protocolIEs				ProtocolIE-Container	{{CommonTransportChannelDeletionResponse-IEs}},
	protocolExtensions		ProtocolExtensionContainer	{{CommonTransportChannelDeletionResponse-Extensions}}     		OPTIONAL,
	...
}

CommonTransportChannelDeletionResponse-IEs NBAP-PROTOCOL-IES ::= {
	{ ID	id-CriticalityDiagnostics		CRITICALITY		ignore		TYPE	CriticalityDiagnostics		PRESENCE	optional},
	...
}

CommonTransportChannelDeletionResponse-Extensions NBAP-PROTOCOL-EXTENSION ::= {
	...
}

-- **************************************************************
--
-- BLOCK RESOURCE REQUEST
--
-- **************************************************************

BlockResourceRequest ::= SEQUENCE {
	protocolIEs				ProtocolIE-Container       {{BlockResourceRequest-IEs}},
	protocolExtensions		ProtocolExtensionContainer	{{BlockResourceRequest-Extensions}}                   OPTIONAL,
	...
}

BlockResourceRequest-IEs NBAP-PROTOCOL-IES ::= {
	{ ID	id-C-ID								CRITICALITY	reject		TYPE	C-ID							PRESENCE	mandatory	}|
	{ ID	id-BlockingPriorityIndicator		CRITICALITY	reject		TYPE	BlockingPriorityIndicator		PRESENCE	mandatory	}|
	{ ID	id-ShutdownTimer					CRITICALITY	reject		TYPE	ShutdownTimer					PRESENCE	conditional	},
	-- The IE shall be present if the Blocking Priority Indicator IE indicates "Normal Priority"--
	...
}

BlockResourceRequest-Extensions NBAP-PROTOCOL-EXTENSION ::= {
	...
}

-- **************************************************************
--
-- BLOCK RESOURCE RESPONSE
--
-- **************************************************************

BlockResourceResponse ::= SEQUENCE {
	protocolIEs					ProtocolIE-Container       {{BlockResourceResponse-IEs}},
	protocolExtensions			ProtocolExtensionContainer	{{BlockResourceResponse-Extensions}}		OPTIONAL,
	...
}

BlockResourceResponse-IEs NBAP-PROTOCOL-IES ::= {
	{ ID	id-CriticalityDiagnostics		CRITICALITY		ignore		TYPE	CriticalityDiagnostics		PRESENCE	optional},
	...
}

BlockResourceResponse-Extensions NBAP-PROTOCOL-EXTENSION ::= {
	...
}

-- **************************************************************
--
-- BLOCK RESOURCE FAILURE
--
-- **************************************************************

BlockResourceFailure ::= SEQUENCE {
	protocolIEs				ProtocolIE-Container       {{BlockResourceFailure-IEs}},
	protocolExtensions		ProtocolExtensionContainer	{{BlockResourceFailure-Extensions}}		OPTIONAL,
	...
}

BlockResourceFailure-IEs NBAP-PROTOCOL-IES ::= {
	{ ID	id-Cause						CRITICALITY		ignore		TYPE	Cause						PRESENCE	mandatory	}|
	{ ID	id-CriticalityDiagnostics		CRITICALITY		ignore		TYPE	CriticalityDiagnostics 		PRESENCE	optional	},
	...
}

BlockResourceFailure-Extensions NBAP-PROTOCOL-EXTENSION ::= {
	...
}

-- **************************************************************
--
-- UNBLOCK RESOURCE INDICATION
--
-- **************************************************************

UnblockResourceIndication ::= SEQUENCE {
	protocolIEs				ProtocolIE-Container	{{UnblockResourceIndication-IEs}},
	protocolExtensions		ProtocolExtensionContainer	{{UnblockResourceIndication-Extensions}}    OPTIONAL,
	...
}

UnblockResourceIndication-IEs NBAP-PROTOCOL-IES ::= {
	{ ID	id-C-ID			CRITICALITY		ignore		TYPE	C-ID		PRESENCE	mandatory},
	...
}

UnblockResourceIndication-Extensions NBAP-PROTOCOL-EXTENSION ::= {
	...
}

-- **************************************************************
--
-- AUDIT REQUIRED INDICATION
--
-- **************************************************************

AuditRequiredIndication ::= SEQUENCE {
	protocolIEs				ProtocolIE-Container	{{AuditRequiredIndication-IEs}},
	protocolExtensions 		ProtocolExtensionContainer	{{AuditRequiredIndication-Extensions}}    	OPTIONAL,
	...
}

AuditRequiredIndication-IEs NBAP-PROTOCOL-IES ::= {
	...
}

AuditRequiredIndication-Extensions NBAP-PROTOCOL-EXTENSION ::= {
	...
}

-- **************************************************************
--
-- AUDIT REQUEST
--
-- **************************************************************

AuditRequest ::= SEQUENCE {
	protocolIEs					ProtocolIE-Container	{{AuditRequest-IEs}},
	protocolExtensions			ProtocolExtensionContainer	{{AuditRequest-Extensions}}		OPTIONAL,
	...
}

AuditRequest-IEs NBAP-PROTOCOL-IES ::= {
	{ ID	id-Start-Of-Audit-Sequence-Indicator		CRITICALITY		reject	TYPE Start-Of-Audit-Sequence-Indicator	 	PRESENCE  mandatory },
	...
}

AuditRequest-Extensions NBAP-PROTOCOL-EXTENSION ::= {
	...
}

-- **************************************************************
--
-- AUDIT RESPONSE
--
-- **************************************************************

AuditResponse ::= SEQUENCE {
	protocolIEs					ProtocolIE-Container	{{AuditResponse-IEs}},
	protocolExtensions			ProtocolExtensionContainer	{{AuditResponse-Extensions}}		OPTIONAL,
	...
}

AuditResponse-IEs NBAP-PROTOCOL-IES ::= {
	{ ID	id-End-Of-Audit-Sequence-Indicator			CRITICALITY		ignore	TYPE 	End-Of-Audit-Sequence-Indicator	 	PRESENCE mandatory }|
	{ ID	id-Cell-InformationList-AuditRsp			CRITICALITY		ignore			TYPE	Cell-InformationList-AuditRsp			PRESENCE	optional	}|
	{ ID	id-CCP-InformationList-AuditRsp				CRITICALITY		ignore			TYPE	CCP-InformationList-AuditRsp			PRESENCE	optional	}|
	-- CCP (Communication Control Port) --
	{ ID	id-Local-Cell-InformationList-AuditRsp		CRITICALITY		ignore			TYPE	Local-Cell-InformationList-AuditRsp		PRESENCE	optional	}|
	{ ID	id-Local-Cell-Group-InformationList-AuditRsp	CRITICALITY		ignore		TYPE	Local-Cell-Group-InformationList-AuditRsp	PRESENCE	optional	}|
	{ ID	id-CriticalityDiagnostics					CRITICALITY		ignore			TYPE	CriticalityDiagnostics					PRESENCE	optional	},
	...
}

AuditResponse-Extensions NBAP-PROTOCOL-EXTENSION ::= {
	{ ID	id-Power-Local-Cell-Group-InformationList-AuditRsp	CRITICALITY		ignore		EXTENSION	Power-Local-Cell-Group-InformationList-AuditRsp		PRESENCE	optional	},
	...
}

Cell-InformationList-AuditRsp ::= SEQUENCE (SIZE (1..maxCellinNodeB)) OF ProtocolIE-Single-Container {{ Cell-InformationItemIE-AuditRsp}}

Cell-InformationItemIE-AuditRsp NBAP-PROTOCOL-IES ::= {
	{ ID	id-Cell-InformationItem-AuditRsp		CRITICALITY		ignore		TYPE	Cell-InformationItem-AuditRsp			PRESENCE 	optional	}
}

Cell-InformationItem-AuditRsp ::= SEQUENCE {
	c-ID									C-ID,
	configurationGenerationID				ConfigurationGenerationID,
	resourceOperationalState				ResourceOperationalState,
	availabilityStatus						AvailabilityStatus,
	local-Cell-ID							Local-Cell-ID,
	primary-SCH-Information					P-SCH-Information-AuditRsp					OPTIONAL,
	secondary-SCH-Information				S-SCH-Information-AuditRsp					OPTIONAL,
	primary-CPICH-Information				P-CPICH-Information-AuditRsp				OPTIONAL,
	secondary-CPICH-InformationList			S-CPICH-InformationList-AuditRsp			OPTIONAL,
	primary-CCPCH-Information				P-CCPCH-Information-AuditRsp				OPTIONAL,
	bCH-Information							BCH-Information-AuditRsp					OPTIONAL,
	secondary-CCPCH-InformationList			S-CCPCH-InformationList-AuditRsp			OPTIONAL,
	pCH-Information							PCH-Information-AuditRsp					OPTIONAL,
	pICH-Information						PICH-Information-AuditRsp					OPTIONAL,
	fACH-InformationList					FACH-InformationList-AuditRsp				OPTIONAL,
	pRACH-InformationList					PRACH-InformationList-AuditRsp				OPTIONAL,
	rACH-InformationList					RACH-InformationList-AuditRsp				OPTIONAL,
	aICH-InformationList					AICH-InformationList-AuditRsp				OPTIONAL,
	pCPCH-InformationList					PCPCH-InformationList-AuditRsp				OPTIONAL,
	cPCH-InformationList					CPCH-InformationList-AuditRsp				OPTIONAL,
	aP-AICH-InformationList					AP-AICH-InformationList-AuditRsp			OPTIONAL,
	cDCA-ICH-InformationList				CDCA-ICH-InformationList-AuditRsp			OPTIONAL,
	sCH-Information							SCH-Information-AuditRsp					OPTIONAL,
	iE-Extensions							ProtocolExtensionContainer  { { Cell-InformationItem-AuditRsp-ExtIEs} }		OPTIONAL,
	...
}

Cell-InformationItem-AuditRsp-ExtIEs NBAP-PROTOCOL-EXTENSION ::= {
	{ ID id-FPACH-LCR-InformationList-AuditRsp		CRITICALITY ignore	EXTENSION 	FPACH-LCR-InformationList-AuditRsp			PRESENCE optional	}|
	-- Applicable to 1.28Mcps TDD only
	{ ID id-DwPCH-LCR-InformationList-AuditRsp		CRITICALITY ignore	EXTENSION	Common-PhysicalChannel-Status-Information				PRESENCE optional	},
	-- Applicable to 1.28Mcps TDD only
	...
}

P-SCH-Information-AuditRsp ::= ProtocolIE-Single-Container {{ P-SCH-InformationIE-AuditRsp }}

P-SCH-InformationIE-AuditRsp NBAP-PROTOCOL-IES ::= {
	{ ID id-P-SCH-Information	CRITICALITY ignore	TYPE Common-PhysicalChannel-Status-Information 	PRESENCE	mandatory }
}

S-SCH-Information-AuditRsp ::= ProtocolIE-Single-Container {{ S-SCH-InformationIE-AuditRsp }}

S-SCH-InformationIE-AuditRsp NBAP-PROTOCOL-IES ::= {
	{ ID id-S-SCH-Information	CRITICALITY ignore	TYPE Common-PhysicalChannel-Status-Information 	PRESENCE	mandatory }
}

P-CPICH-Information-AuditRsp ::= ProtocolIE-Single-Container {{ P-CPICH-InformationIE-AuditRsp }}

P-CPICH-InformationIE-AuditRsp NBAP-PROTOCOL-IES ::= {
	{ ID id-P-CPICH-Information	CRITICALITY ignore	TYPE Common-PhysicalChannel-Status-Information 	PRESENCE	mandatory }
}

S-CPICH-InformationList-AuditRsp ::= SEQUENCE (SIZE (1..maxSCPICHCell)) OF ProtocolIE-Single-Container {{ S-CPICH-InformationItemIE-AuditRsp }}

S-CPICH-InformationItemIE-AuditRsp NBAP-PROTOCOL-IES ::= {
	{ ID id-S-CPICH-Information   CRITICALITY ignore	TYPE Common-PhysicalChannel-Status-Information		PRESENCE mandatory }
}

P-CCPCH-Information-AuditRsp ::= ProtocolIE-Single-Container {{ P-CCPCH-InformationIE-AuditRsp }}

P-CCPCH-InformationIE-AuditRsp NBAP-PROTOCOL-IES ::= {
	{ ID id-P-CCPCH-Information   CRITICALITY ignore	TYPE Common-PhysicalChannel-Status-Information		PRESENCE mandatory }
}

BCH-Information-AuditRsp ::= ProtocolIE-Single-Container {{ BCH-InformationIE-AuditRsp }}

BCH-InformationIE-AuditRsp NBAP-PROTOCOL-IES ::= {
	{ ID id-BCH-Information   CRITICALITY ignore	TYPE Common-TransportChannel-Status-Information		PRESENCE mandatory }
}

S-CCPCH-InformationList-AuditRsp ::= SEQUENCE (SIZE (1..maxSCCPCHCell)) OF ProtocolIE-Single-Container {{ S-CCPCH-InformationItemIE-AuditRsp }}

S-CCPCH-InformationItemIE-AuditRsp NBAP-PROTOCOL-IES ::= {
	{ ID id-S-CCPCH-Information   CRITICALITY ignore	TYPE Common-PhysicalChannel-Status-Information		PRESENCE mandatory }
}
PCH-Information-AuditRsp ::= ProtocolIE-Single-Container {{ PCH-InformationIE-AuditRsp }}

PCH-InformationIE-AuditRsp NBAP-PROTOCOL-IES ::= {
	{ ID id-PCH-Information   CRITICALITY ignore	TYPE Common-TransportChannel-Status-Information		PRESENCE mandatory }
}

PICH-Information-AuditRsp ::= ProtocolIE-Single-Container {{ PICH-InformationIE-AuditRsp }}

PICH-InformationIE-AuditRsp NBAP-PROTOCOL-IES ::= {
	{ ID id-PICH-Information   CRITICALITY ignore	TYPE Common-PhysicalChannel-Status-Information		PRESENCE mandatory }
}

FACH-InformationList-AuditRsp ::= SEQUENCE (SIZE (1..maxFACHCell)) OF ProtocolIE-Single-Container {{ FACH-InformationItemIE-AuditRsp }}

FACH-InformationItemIE-AuditRsp NBAP-PROTOCOL-IES ::= {
	{ ID id-FACH-Information   CRITICALITY ignore	TYPE Common-TransportChannel-Status-Information		PRESENCE mandatory }
}

PRACH-InformationList-AuditRsp ::= SEQUENCE (SIZE (1..maxPRACHCell)) OF ProtocolIE-Single-Container {{ PRACH-InformationItemIE-AuditRsp }}

PRACH-InformationItemIE-AuditRsp NBAP-PROTOCOL-IES ::= {
	{ ID id-PRACH-Information   CRITICALITY ignore	TYPE Common-PhysicalChannel-Status-Information		PRESENCE mandatory }
}

RACH-InformationList-AuditRsp ::= SEQUENCE (SIZE (1..maxRACHCell)) OF ProtocolIE-Single-Container {{ RACH-InformationItemIE-AuditRsp }}

RACH-InformationItemIE-AuditRsp NBAP-PROTOCOL-IES ::= {
	{ ID id-RACH-Information   CRITICALITY ignore	TYPE Common-TransportChannel-Status-Information		PRESENCE mandatory }
}

AICH-InformationList-AuditRsp ::= SEQUENCE (SIZE (1..maxPRACHCell)) OF ProtocolIE-Single-Container {{ AICH-InformationItemIE-AuditRsp }}

AICH-InformationItemIE-AuditRsp NBAP-PROTOCOL-IES ::= {
	{ ID id-AICH-Information   CRITICALITY ignore	TYPE Common-PhysicalChannel-Status-Information		PRESENCE mandatory }
}

PCPCH-InformationList-AuditRsp ::= SEQUENCE (SIZE (1..maxPCPCHCell)) OF ProtocolIE-Single-Container {{ PCPCH-InformationItemIE-AuditRsp }}

PCPCH-InformationItemIE-AuditRsp NBAP-PROTOCOL-IES ::= {
	{ ID id-PCPCH-Information   CRITICALITY ignore	TYPE Common-PhysicalChannel-Status-Information		PRESENCE optional }
}

CPCH-InformationList-AuditRsp ::= SEQUENCE (SIZE (1..maxCPCHCell)) OF ProtocolIE-Single-Container {{ CPCH-InformationItemIE-AuditRsp }}

CPCH-InformationItemIE-AuditRsp NBAP-PROTOCOL-IES ::= {
	{ ID id-CPCH-Information   CRITICALITY ignore	TYPE Common-TransportChannel-Status-Information		PRESENCE optional }
}

AP-AICH-InformationList-AuditRsp ::= SEQUENCE (SIZE (1..maxCPCHCell)) OF ProtocolIE-Single-Container {{ AP-AICH-InformationItemIE-AuditRsp }}

AP-AICH-InformationItemIE-AuditRsp NBAP-PROTOCOL-IES ::= {
	{ ID id-AP-AICH-Information   CRITICALITY ignore	TYPE Common-PhysicalChannel-Status-Information		PRESENCE mandatory }
}

CDCA-ICH-InformationList-AuditRsp ::= SEQUENCE (SIZE (1..maxCPCHCell)) OF ProtocolIE-Single-Container {{ CDCA-ICH-InformationItemIE-AuditRsp }}

CDCA-ICH-InformationItemIE-AuditRsp NBAP-PROTOCOL-IES ::= {
	{ ID id-CDCA-ICH-Information   CRITICALITY ignore	TYPE Common-PhysicalChannel-Status-Information		PRESENCE mandatory }
}

SCH-Information-AuditRsp ::= ProtocolIE-Single-Container {{ SCH-InformationIE-AuditRsp }}

SCH-InformationIE-AuditRsp NBAP-PROTOCOL-IES ::= {
	{ ID id-SCH-Information   CRITICALITY ignore	TYPE Common-PhysicalChannel-Status-Information		PRESENCE mandatory }
}

CCP-InformationList-AuditRsp ::=SEQUENCE (SIZE (1..maxCCPinNodeB)) OF ProtocolIE-Single-Container {{ CCP-InformationItemIE-AuditRsp }}

CCP-InformationItemIE-AuditRsp NBAP-PROTOCOL-IES ::= {
	{ID	id-CCP-InformationItem-AuditRsp			CRITICALITY		ignore			TYPE	CCP-InformationItem-AuditRsp			PRESENCE	mandatory}
}	

CCP-InformationItem-AuditRsp ::= SEQUENCE {
	communicationControlPortID			CommunicationControlPortID,
	resourceOperationalState			ResourceOperationalState,
	availabilityStatus					AvailabilityStatus,
	iE-Extensions						ProtocolExtensionContainer  {{ CCP-InformationItem-AuditRsp-ExtIEs }}		OPTIONAL,
	...
}

CCP-InformationItem-AuditRsp-ExtIEs NBAP-PROTOCOL-EXTENSION ::= {
	...
}

FPACH-LCR-InformationList-AuditRsp ::= SEQUENCE (SIZE (1..maxFPACHCell)) OF ProtocolIE-Single-Container {{ FPACH-LCR-InformationItemIE-AuditRsp }}

FPACH-LCR-InformationItemIE-AuditRsp NBAP-PROTOCOL-IES ::= {
	{ ID id-FPACH-LCR-Information-AuditRsp   CRITICALITY ignore	TYPE Common-PhysicalChannel-Status-Information		PRESENCE mandatory }
}

Local-Cell-InformationList-AuditRsp	 ::=SEQUENCE (SIZE (1..maxLocalCellinNodeB)) OF ProtocolIE-Single-Container {{ Local-Cell-InformationItemIE-AuditRsp }}

Local-Cell-InformationItemIE-AuditRsp NBAP-PROTOCOL-IES ::= {
	{ ID	id-Local-Cell-InformationItem-AuditRsp			CRITICALITY		ignore			TYPE	Local-Cell-InformationItem-AuditRsp		PRESENCE	mandatory}
}

Local-Cell-InformationItem-AuditRsp ::= SEQUENCE {
	local-Cell-ID								Local-Cell-ID,
	dl-or-global-capacityCredit					DL-or-Global-CapacityCredit,
	ul-capacityCredit							UL-CapacityCredit		OPTIONAL,
	commonChannelsCapacityConsumptionLaw 		CommonChannelsCapacityConsumptionLaw,
	dedicatedChannelsCapacityConsumptionLaw 	DedicatedChannelsCapacityConsumptionLaw,
	maximumDL-PowerCapability					MaximumDL-PowerCapability		OPTIONAL,
	minSpreadingFactor							MinSpreadingFactor				OPTIONAL,
	minimumDL-PowerCapability					MinimumDL-PowerCapability		OPTIONAL,
	local-Cell-Group-ID							Local-Cell-ID					OPTIONAL,
	iE-Extensions								ProtocolExtensionContainer  {{ Local-Cell-InformationItem-AuditRsp-ExtIEs}}		OPTIONAL,
	...
}

Local-Cell-InformationItem-AuditRsp-ExtIEs NBAP-PROTOCOL-EXTENSION ::= {
	{ ID	id-ReferenceClockAvailability		CRITICALITY		ignore			EXTENSION ReferenceClockAvailability			PRESENCE	optional }|
	{ ID	id-Power-Local-Cell-Group-ID		CRITICALITY		ignore			EXTENSION	Local-Cell-ID				PRESENCE	optional },
	...
}

Local-Cell-Group-InformationList-AuditRsp	 ::= SEQUENCE (SIZE (1..maxLocalCellinNodeB)) OF ProtocolIE-Single-Container {{ Local-Cell-Group-InformationItemIE-AuditRsp }}

Local-Cell-Group-InformationItemIE-AuditRsp NBAP-PROTOCOL-IES ::= {
	{ ID	id-Local-Cell-Group-InformationItem-AuditRsp			CRITICALITY		ignore			TYPE	Local-Cell-Group-InformationItem-AuditRsp		PRESENCE	mandatory}
}

Local-Cell-Group-InformationItem-AuditRsp ::= SEQUENCE {
	local-Cell-Group-ID							Local-Cell-ID,
	dl-or-global-capacityCredit					DL-or-Global-CapacityCredit,
	ul-capacityCredit							UL-CapacityCredit						OPTIONAL,
	commonChannelsCapacityConsumptionLaw 		CommonChannelsCapacityConsumptionLaw,
	dedicatedChannelsCapacityConsumptionLaw 	DedicatedChannelsCapacityConsumptionLaw,
	iE-Extensions								ProtocolExtensionContainer  {{ Local-Cell-Group-InformationItem-AuditRsp-ExtIEs}}		OPTIONAL,
	...
}

Local-Cell-Group-InformationItem-AuditRsp-ExtIEs NBAP-PROTOCOL-EXTENSION ::= {
	...
}

Power-Local-Cell-Group-InformationList-AuditRsp	 ::= SEQUENCE (SIZE (1..maxLocalCellinNodeB)) OF ProtocolIE-Single-Container {{ Power-Local-Cell-Group-InformationItemIE-AuditRsp }}

Power-Local-Cell-Group-InformationItemIE-AuditRsp NBAP-PROTOCOL-IES ::= {
	{ ID	id-Power-Local-Cell-Group-InformationItem-AuditRsp			CRITICALITY		ignore			TYPE	Power-Local-Cell-Group-InformationItem-AuditRsp		PRESENCE	mandatory}
}

Power-Local-Cell-Group-InformationItem-AuditRsp ::= SEQUENCE {
	power-Local-Cell-Group-ID					Local-Cell-ID,
	maximumDL-PowerCapability					MaximumDL-PowerCapability,
	iE-Extensions								ProtocolExtensionContainer  {{ Power-Local-Cell-Group-InformationItem-AuditRsp-ExtIEs}}		OPTIONAL,
	...
}

Power-Local-Cell-Group-InformationItem-AuditRsp-ExtIEs NBAP-PROTOCOL-EXTENSION ::= {
	...
}

-- **************************************************************
--
-- AUDIT FAILURE
--
-- **************************************************************

AuditFailure ::= SEQUENCE {
	protocolIEs				ProtocolIE-Container	{{AuditFailure-IEs}},
	protocolExtensions		ProtocolExtensionContainer	{{AuditFailure-Extensions}}			OPTIONAL,
	...
}

AuditFailure-IEs NBAP-PROTOCOL-IES ::= {
	{ ID	id-Cause							CRITICALITY		ignore			TYPE	Cause						PRESENCE	mandatory	}|
	{ ID	id-CriticalityDiagnostics			CRITICALITY		ignore			TYPE	CriticalityDiagnostics		PRESENCE	optional	},
	...
}

AuditFailure-Extensions NBAP-PROTOCOL-EXTENSION ::= {
	...
}

-- **************************************************************
--
-- COMMON MEASUREMENT INITIATION REQUEST
--
-- **************************************************************

CommonMeasurementInitiationRequest ::= SEQUENCE {
	protocolIEs				ProtocolIE-Container	{{CommonMeasurementInitiationRequest-IEs}},
	protocolExtensions		ProtocolExtensionContainer	{{CommonMeasurementInitiationRequest-Extensions}}		OPTIONAL,
	...
}

CommonMeasurementInitiationRequest-IEs NBAP-PROTOCOL-IES ::= {
	{ ID	id-MeasurementID								CRITICALITY	reject			TYPE	MeasurementID							PRESENCE	mandatory	}|
	{ ID	id-CommonMeasurementObjectType-CM-Rqst			CRITICALITY	reject			TYPE 	CommonMeasurementObjectType-CM-Rqst		PRESENCE 	mandatory	}|
	{ ID	id-CommonMeasurementType						CRITICALITY	reject			TYPE	CommonMeasurementType					PRESENCE	mandatory	}|
	{ ID 	id-MeasurementFilterCoefficient					CRITICALITY	reject			TYPE	MeasurementFilterCoefficient				PRESENCE	optional	}|
	{ ID	id-ReportCharacteristics						CRITICALITY	reject			TYPE	ReportCharacteristics					PRESENCE	mandatory	}|
	{ ID	id-SFNReportingIndicator						CRITICALITY	reject			TYPE	FNReportingIndicator					PRESENCE	mandatory
    } |
    { ID    id-SFN                                          CRITICALITY reject          TYPE    SFN                          		PRESENCE optional
	},
	...
}

CommonMeasurementInitiationRequest-Extensions NBAP-PROTOCOL-EXTENSION ::= {
	{ID id-CommonMeasurementAccuracy						CRITICALITY reject			EXTENSION CommonMeasurementAccuracy			PRESENCE optional},
	...
}

CommonMeasurementObjectType-CM-Rqst ::= CHOICE {
	cell							Cell-CM-Rqst,
	rACH							RACH-CM-Rqst,
	cPCH							CPCH-CM-Rqst,
	...
}

Cell-CM-Rqst ::= SEQUENCE {
	c-ID							C-ID,
	timeSlot						TimeSlot	OPTIONAL, 	-- Applicable to 3.84Mcps TDD only
	iE-Extensions					ProtocolExtensionContainer  { { CellItem-CM-Rqst-ExtIEs} }		OPTIONAL,
	...
}

CellItem-CM-Rqst-ExtIEs NBAP-PROTOCOL-EXTENSION ::= {
	{ ID id-TimeSlotLCR-CM-Rqst		CRITICALITY reject		EXTENSION 	TimeSlotLCR			PRESENCE optional	}|
	-- Applicable to 1.28Mcps TDD only
	{ID id-NeighbouringCellMeasurementInformation		CRITICALITY ignore			EXTENSION NeighbouringCellMeasurementInformation			PRESENCE optional},
	...
}

RACH-CM-Rqst ::= SEQUENCE {
	c-ID							C-ID,
	commonTransportChannelID		CommonTransportChannelID,
	iE-Extensions					ProtocolExtensionContainer  { { RACHItem-CM-Rqst-ExtIEs} }		OPTIONAL,
	...
}

RACHItem-CM-Rqst-ExtIEs NBAP-PROTOCOL-EXTENSION ::= {
	...
}

CPCH-CM-Rqst ::= SEQUENCE {
	c-ID							C-ID,
	commonTransportChannelID		CommonTransportChannelID,
	spreadingfactor					MinUL-ChannelisationCodeLength		OPTIONAL,
	iE-Extensions					ProtocolExtensionContainer  { { CPCHItem-CM-Rqst-ExtIEs} }		OPTIONAL,
	...
}

CPCHItem-CM-Rqst-ExtIEs NBAP-PROTOCOL-EXTENSION ::= {
	...
}

-- **************************************************************
--
-- COMMON MEASUREMENT INITIATION RESPONSE
--
-- **************************************************************

CommonMeasurementInitiationResponse ::= SEQUENCE {
	protocolIEs				ProtocolIE-Container	{{CommonMeasurementInitiationResponse-IEs}},
	protocolExtensions		ProtocolExtensionContainer	{{CommonMeasurementInitiationResponse-Extensions}}		OPTIONAL,
	...
}

CommonMeasurementInitiationResponse-IEs NBAP-PROTOCOL-IES ::= {
	{ ID	id-MeasurementID							CRITICALITY	ignore			TYPE	MeasurementID							PRESENCE	mandatory	}|
	{ ID	id-CommonMeasurementObjectType-CM-Rsp		CRITICALITY	ignore			TYPE	CommonMeasurementObjectType-CM-Rsp		PRESENCE	optional	}|
	{ ID	id-SFN										CRITICALITY	ignore			TYPE	SFN										PRESENCE	optional	}|
	{ ID	id-CriticalityDiagnostics					CRITICALITY	ignore			TYPE	CriticalityDiagnostics					PRESENCE	optional	},
	...
}

CommonMeasurementInitiationResponse-Extensions NBAP-PROTOCOL-EXTENSION ::= {
	{ID id-CommonMeasurementAccuracy		CRITICALITY ignore		EXTENSION CommonMeasurementAccuracy	 PRESENCE optional},
	...
}

CommonMeasurementObjectType-CM-Rsp ::= CHOICE {
 	cell						Cell-CM-Rsp,
 	rACH						RACH-CM-Rsp,
	cPCH						CPCH-CM-Rsp,
	...
 }

Cell-CM-Rsp ::= SEQUENCE {
 	commonMeasurementValue			CommonMeasurementValue,
	iE-Extensions					ProtocolExtensionContainer  { { CellItem-CM-Rsp-ExtIEs} }		OPTIONAL,
	...
 }

CellItem-CM-Rsp-ExtIEs NBAP-PROTOCOL-EXTENSION ::= {
	...
}

RACH-CM-Rsp ::= SEQUENCE {
 	commonMeasurementValue			CommonMeasurementValue,
	iE-Extensions					ProtocolExtensionContainer  { { RACHItem-CM-Rsp-ExtIEs} }		OPTIONAL,
	...
 }

RACHItem-CM-Rsp-ExtIEs NBAP-PROTOCOL-EXTENSION ::= {
	...
}

CPCH-CM-Rsp ::= SEQUENCE {
 	commonMeasurementValue			CommonMeasurementValue,
	iE-Extensions					ProtocolExtensionContainer  { { CPCHItem-CM-Rsp-ExtIEs} }		OPTIONAL,
	...
 }

CPCHItem-CM-Rsp-ExtIEs NBAP-PROTOCOL-EXTENSION ::= {
	...
}

-- **************************************************************
--
-- COMMON MEASUREMENT INITIATION FAILURE
--
-- **************************************************************

CommonMeasurementInitiationFailure ::= SEQUENCE {
	protocolIEs				ProtocolIE-Container	{{CommonMeasurementInitiationFailure-IEs}},
	protocolExtensions		ProtocolExtensionContainer	{{CommonMeasurementInitiationFailure-Extensions}}		OPTIONAL,
	...
}

CommonMeasurementInitiationFailure-IEs NBAP-PROTOCOL-IES ::= {
	{ ID	id-MeasurementID				CRITICALITY		ignore			TYPE	MeasurementID				PRESENCE	mandatory	}|
	{ ID	id-Cause						CRITICALITY		ignore			TYPE	Cause						PRESENCE	mandatory	}|
	{ ID	id-CriticalityDiagnostics		CRITICALITY		ignore			TYPE	CriticalityDiagnostics		PRESENCE	optional	},
	...
}

CommonMeasurementInitiationFailure-Extensions NBAP-PROTOCOL-EXTENSION ::= {
	...
}

-- **************************************************************
--
-- COMMON MEASUREMENT REPORT
--
-- **************************************************************

CommonMeasurementReport ::= SEQUENCE {
	protocolIEs				ProtocolIE-Container	{{CommonMeasurementReport-IEs}},
	protocolExtensions		ProtocolExtensionContainer	{{CommonMeasurementReport-Extensions}}		OPTIONAL,
	...
}

CommonMeasurementReport-IEs NBAP-PROTOCOL-IES ::= {
	{ ID	id-MeasurementID							CRITICALITY	ignore			TYPE	MeasurementID							PRESENCE	mandatory	}|
	{ ID	id-CommonMeasurementObjectType-CM-Rprt		CRITICALITY	ignore			TYPE	CommonMeasurementObjectType-CM-Rprt		PRESENCE	mandatory	}|
	{ ID	id-SFN										CRITICALITY	ignore			TYPE	SFN										PRESENCE	optional	},
	...
}

CommonMeasurementReport-Extensions NBAP-PROTOCOL-EXTENSION ::= {
	...
}

CommonMeasurementObjectType-CM-Rprt ::= CHOICE {
	cell							Cell-CM-Rprt,
	rACH							RACH-CM-Rprt,
	cPCH							CPCH-CM-Rprt,
	...
 }

Cell-CM-Rprt ::= SEQUENCE {
	commonMeasurementValueInformation	CommonMeasurementValueInformation,
	iE-Extensions					ProtocolExtensionContainer  {{ CellItem-CM-Rprt-ExtIEs }}		OPTIONAL,
	...

 }

CellItem-CM-Rprt-ExtIEs NBAP-PROTOCOL-EXTENSION ::= {
	...
}


RACH-CM-Rprt ::= SEQUENCE {
	commonMeasurementValueInformation	CommonMeasurementValueInformation,
	iE-Extensions					ProtocolExtensionContainer {{ RACHItem-CM-Rprt-ExtIEs }}			OPTIONAL,
	...
 }

RACHItem-CM-Rprt-ExtIEs NBAP-PROTOCOL-EXTENSION ::= {
	...
}

CPCH-CM-Rprt ::= SEQUENCE {
	commonMeasurementValueInformation	CommonMeasurementValueInformation,
	iE-Extensions					ProtocolExtensionContainer {{ CPCHItem-CM-Rprt-ExtIEs }}			OPTIONAL,
	...
 }

CPCHItem-CM-Rprt-ExtIEs NBAP-PROTOCOL-EXTENSION ::= {
	...
}

-- **************************************************************
--
-- COMMON MEASUREMENT TERMINATION REQUEST
--
-- **************************************************************

CommonMeasurementTerminationRequest ::= SEQUENCE {
	protocolIEs				ProtocolIE-Container	{{CommonMeasurementTerminationRequest-IEs}},
	protocolExtensions		ProtocolExtensionContainer	{{CommonMeasurementTerminationRequest-Extensions}}		OPTIONAL,
	...
}

CommonMeasurementTerminationRequest-IEs NBAP-PROTOCOL-IES ::= {
	{ ID	id-MeasurementID			CRITICALITY		ignore				TYPE	MeasurementID			PRESENCE	mandatory},
	...
}

CommonMeasurementTerminationRequest-Extensions NBAP-PROTOCOL-EXTENSION ::= {
	...
}

-- **************************************************************
--
-- COMMON MEASUREMENT FAILURE INDICATION
--
-- **************************************************************

CommonMeasurementFailureIndication ::= SEQUENCE {
	protocolIEs				ProtocolIE-Container	{{CommonMeasurementFailureIndication-IEs}},
	protocolExtensions			ProtocolExtensionContainer	{{CommonMeasurementFailureIndication-Extensions}}				OPTIONAL,
	...
}

CommonMeasurementFailureIndication-IEs NBAP-PROTOCOL-IES ::= {
	{ ID	id-MeasurementID			CRITICALITY	ignore			TYPE	MeasurementID			PRESENCE	mandatory	}|
	{ ID	id-Cause					CRITICALITY	ignore			TYPE	Cause					PRESENCE	mandatory	},
	...
}

CommonMeasurementFailureIndication-Extensions NBAP-PROTOCOL-EXTENSION ::= {
	...
}

-- **************************************************************
--
-- CELL SETUP REQUEST FDD
--
-- **************************************************************

CellSetupRequestFDD ::= SEQUENCE {
	protocolIEs				ProtocolIE-Container	{{CellSetupRequestFDD-IEs}},
	protocolExtensions		ProtocolExtensionContainer	{{CellSetupRequestFDD-Extensions}}		OPTIONAL,
	...
}

CellSetupRequestFDD-IEs NBAP-PROTOCOL-IES ::= {
	{ ID	id-Local-Cell-ID										CRITICALITY		reject			TYPE	Local-Cell-ID									PRESENCE	mandatory	}|
	{ ID	id-C-ID													CRITICALITY		reject			TYPE	C-ID											PRESENCE 	mandatory	}|
	{ ID	id-ConfigurationGenerationID							CRITICALITY		reject			TYPE	ConfigurationGenerationID						PRESENCE	mandatory	}|
	{ ID	id-T-Cell												CRITICALITY		reject			TYPE	T-Cell											PRESENCE	mandatory	}|
	{ ID	id-UARFCNforNu											CRITICALITY		reject			TYPE	UARFCN											PRESENCE	mandatory	}|
	{ ID	id-UARFCNforNd											CRITICALITY		reject			TYPE	UARFCN											PRESENCE	mandatory	}|
	{ ID	id-MaximumTransmissionPower								CRITICALITY		reject			TYPE	MaximumTransmissionPower						PRESENCE	mandatory	}|
	{ ID	id-Closed-Loop-Timing-Adjustment-Mode					CRITICALITY		reject			TYPE	Closedlooptimingadjustmentmode					PRESENCE	optional	}|
	{ ID	id-PrimaryScramblingCode								CRITICALITY		reject			TYPE	PrimaryScramblingCode							PRESENCE	mandatory	}|
	{ ID	id-Synchronisation-Configuration-Cell-SetupRqst			CRITICALITY		reject			TYPE	Synchronisation-Configuration-Cell-SetupRqst			PRESENCE	mandatory	}|
	{ ID	id-DL-TPC-Pattern01Count								CRITICALITY		reject				TYPE	DL-TPC-Pattern01Count							PRESENCE	mandatory	}|
	{ ID	id-PrimarySCH-Information-Cell-SetupRqstFDD				CRITICALITY		reject			TYPE	PrimarySCH-Information-Cell-SetupRqstFDD			PRESENCE	mandatory	}|
	{ ID	id-SecondarySCH-Information-Cell-SetupRqstFDD			CRITICALITY		reject			TYPE	SecondarySCH-Information-Cell-SetupRqstFDD		PRESENCE	mandatory	}|
	{ ID	id-PrimaryCPICH-Information-Cell-SetupRqstFDD			CRITICALITY		reject			TYPE	PrimaryCPICH-Information-Cell-SetupRqstFDD		PRESENCE	mandatory	}|
	{ ID	id-SecondaryCPICH-InformationList-Cell-SetupRqstFDD		CRITICALITY		reject			TYPE	SecondaryCPICH-InformationList-Cell-SetupRqstFDD		PRESENCE	optional	}|
	{ ID	id-PrimaryCCPCH-Information-Cell-SetupRqstFDD			CRITICALITY		reject			TYPE	PrimaryCCPCH-Information-Cell-SetupRqstFDD		PRESENCE	mandatory	}|
	{ ID	id-Limited-power-increase-information-Cell-SetupRqstFDD	CRITICALITY		reject			TYPE	Limited-power-increase-information-Cell-SetupRqstFDD		PRESENCE	mandatory	},
	...
}

CellSetupRequestFDD-Extensions NBAP-PROTOCOL-EXTENSION ::= {
	{ID	id-IPDLParameter-Information-Cell-SetupRqstFDD				CRITICALITY		reject		EXTENSION		IPDLParameter-Information-Cell-SetupRqstFDD		PRESENCE	optional	}|
	{ID	id-PDSCH-Information-Cell-SetupRqstFDD				CRITICALITY		reject		EXTENSION		PDSCH-Information-Cell-SetupRqstFDD		PRESENCE	optional	},
	...
}

Synchronisation-Configuration-Cell-SetupRqst ::= SEQUENCE {
	n-INSYNC-IND			N-INSYNC-IND,
 	n-OUTSYNC-IND			N-OUTSYNC-IND,
 	t-RLFAILURE				T-RLFAILURE,
	iE-Extensions			ProtocolExtensionContainer { { Synchronisation-Configuration-Cell-SetupRqst-ExtIEs} }		OPTIONAL,
	...
}

Synchronisation-Configuration-Cell-SetupRqst-ExtIEs NBAP-PROTOCOL-EXTENSION ::= {
	...
}

PrimarySCH-Information-Cell-SetupRqstFDD ::= SEQUENCE {
	commonPhysicalChannelID					CommonPhysicalChannelID,
	primarySCH-Power						DL-Power,
	tSTD-Indicator							TSTD-Indicator,
	iE-Extensions							ProtocolExtensionContainer { { PrimarySCH-Information-Cell-SetupRqstFDD-ExtIEs} }		OPTIONAL,
	...
}

PrimarySCH-Information-Cell-SetupRqstFDD-ExtIEs NBAP-PROTOCOL-EXTENSION ::= {
	...
}

SecondarySCH-Information-Cell-SetupRqstFDD ::= SEQUENCE {
	commonPhysicalChannelID					CommonPhysicalChannelID,
	secondarySCH-Power						DL-Power,
	tSTD-Indicator							TSTD-Indicator,
	iE-Extensions							ProtocolExtensionContainer { { SecondarySCH-Information-Cell-SetupRqstFDD-ExtIEs} }		OPTIONAL,
	...
}

SecondarySCH-Information-Cell-SetupRqstFDD-ExtIEs NBAP-PROTOCOL-EXTENSION ::= {
	...
}

PrimaryCPICH-Information-Cell-SetupRqstFDD ::= SEQUENCE {
	commonPhysicalChannelID					CommonPhysicalChannelID,
	primaryCPICH-Power						PrimaryCPICH-Power,
	transmitDiversityIndicator				TransmitDiversityIndicator,
	iE-Extensions							ProtocolExtensionContainer { { PrimaryCPICH-Information-Cell-SetupRqstFDD-ExtIEs} }		OPTIONAL,
	...
}

PrimaryCPICH-Information-Cell-SetupRqstFDD-ExtIEs NBAP-PROTOCOL-EXTENSION ::= {
	...
}

SecondaryCPICH-InformationList-Cell-SetupRqstFDD ::= SEQUENCE (SIZE (1..maxSCPICHCell)) OF ProtocolIE-Single-Container{{ SecondaryCPICH-InformationItemIE-Cell-SetupRqstFDD }}

SecondaryCPICH-InformationItemIE-Cell-SetupRqstFDD NBAP-PROTOCOL-IES ::= {
	{ ID	id-SecondaryCPICH-InformationItem-Cell-SetupRqstFDD		CRITICALITY		reject			TYPE	SecondaryCPICH-InformationItem-Cell-SetupRqstFDD		PRESENCE	mandatory}
}

SecondaryCPICH-InformationItem-Cell-SetupRqstFDD ::= SEQUENCE {
	commonPhysicalChannelID					CommonPhysicalChannelID,
	dl-ScramblingCode						DL-ScramblingCode,
	fDD-DL-ChannelisationCodeNumber			FDD-DL-ChannelisationCodeNumber,
	secondaryCPICH-Power					DL-Power,
	transmitDiversityIndicator				TransmitDiversityIndicator,
	iE-Extensions							ProtocolExtensionContainer { { SecondaryCPICH-InformationItem-Cell-SetupRqstFDD-ExtIEs} }		OPTIONAL,
	...
}

SecondaryCPICH-InformationItem-Cell-SetupRqstFDD-ExtIEs NBAP-PROTOCOL-EXTENSION ::= {
	...
}

PrimaryCCPCH-Information-Cell-SetupRqstFDD ::= SEQUENCE {
	commonPhysicalChannelID					CommonPhysicalChannelID,
	bCH-information							BCH-Information-Cell-SetupRqstFDD,
	sTTD-Indicator							STTD-Indicator,
	iE-Extensions							ProtocolExtensionContainer { { PrimaryCCPCH-Information-Cell-SetupRqstFDD-ExtIEs} }		OPTIONAL,
	...
}

PrimaryCCPCH-Information-Cell-SetupRqstFDD-ExtIEs NBAP-PROTOCOL-EXTENSION ::= {
	...
}

BCH-Information-Cell-SetupRqstFDD ::= SEQUENCE {
 	commonTransportChannelID				CommonTransportChannelID,
 	bCH-Power								DL-Power,
	iE-Extensions							ProtocolExtensionContainer { { BCH-Information-Cell-SetupRqstFDD-ExtIEs} }		OPTIONAL,
	...
 }

BCH-Information-Cell-SetupRqstFDD-ExtIEs NBAP-PROTOCOL-EXTENSION ::= {
	...
}

Limited-power-increase-information-Cell-SetupRqstFDD ::= SEQUENCE {
	powerRaiseLimit							PowerRaiseLimit,
	dLPowerAveragingWindowSize				DLPowerAveragingWindowSize,
	iE-Extensions							ProtocolExtensionContainer { { Limited-power-increase-information-Cell-SetupRqstFDD-ExtIEs} }		OPTIONAL,
	...
}

Limited-power-increase-information-Cell-SetupRqstFDD-ExtIEs NBAP-PROTOCOL-EXTENSION ::= {
	...
}

IPDLParameter-Information-Cell-SetupRqstFDD::= SEQUENCE {
	iPDL-FDD-Parameters							IPDL-FDD-Parameters,
	iPDL-Indicator								IPDL-Indicator,	
	iE-Extensions							ProtocolExtensionContainer { { IPDLParameter-Information-Cell-SetupRqstFDD-ExtIEs} }		OPTIONAL,
	...
}

IPDLParameter-Information-Cell-SetupRqstFDD-ExtIEs NBAP-PROTOCOL-EXTENSION ::= {
	...
}

PDSCH-Information-Cell-SetupRqstFDD	::= SEQUENCE {
	maximum-PDSCH-Power		Maximum-PDSCH-Power,
	iE-Extensions			ProtocolExtensionContainer { { PDSCH-Information-Cell-SetupRqstFDD-ExtIEs} }		OPTIONAL,
	...
}

PDSCH-Information-Cell-SetupRqstFDD-ExtIEs NBAP-PROTOCOL-EXTENSION ::= {
	...
}

-- **************************************************************
--
-- CELL SETUP REQUEST TDD
--
-- **************************************************************

CellSetupRequestTDD ::= SEQUENCE {
	protocolIEs				ProtocolIE-Container	{{CellSetupRequestTDD-IEs}},
	protocolExtensions		ProtocolExtensionContainer	{{CellSetupRequestTDD-Extensions}}		OPTIONAL,
	...
}

CellSetupRequestTDD-IEs NBAP-PROTOCOL-IES ::= {
	{ ID	id-Local-Cell-ID									CRITICALITY		reject		TYPE	Local-Cell-ID									PRESENCE	mandatory	}|
		{ ID	id-C-ID												CRITICALITY		reject		TYPE	C-ID											PRESENCE 	mandatory	}|
	{ ID	id-ConfigurationGenerationID						CRITICALITY		reject		TYPE	ConfigurationGenerationID						PRESENCE	mandatory	}|
	{ ID	id-UARFCNforNt											CRITICALITY		reject		TYPE	UARFCN											PRESENCE	mandatory	}|
	{ ID	id-CellParameterID									CRITICALITY		reject		TYPE	CellParameterID									PRESENCE	mandatory	}|
	{ ID	id-MaximumTransmissionPower							CRITICALITY		reject		TYPE	MaximumTransmissionPower						PRESENCE	mandatory	}|
	{ ID	id-TransmissionDiversityApplied						CRITICALITY		reject		TYPE	TransmissionDiversityApplied					PRESENCE	mandatory	}|
	{ ID	id-SyncCase											CRITICALITY		reject		TYPE	SyncCase										PRESENCE 	mandatory	}|
	{ ID	id-Synchronisation-Configuration-Cell-SetupRqst		CRITICALITY		reject		TYPE	Synchronisation-Configuration-Cell-SetupRqst		PRESENCE	mandatory	}|
	{ ID	id-DPCHConstant										CRITICALITY		reject		TYPE	ConstantValue										PRESENCE 	mandatory	}|
	{ ID	id-PUSCHConstant									CRITICALITY		reject		TYPE	ConstantValue										PRESENCE 	mandatory	}|
	{ ID	id-PRACHConstant									CRITICALITY		reject		TYPE	ConstantValue										PRESENCE 	mandatory	}|
    { ID	id-TimingAdvanceApplied								CRITICALITY		reject		TYPE	TimingAdvanceApplied								PRESENCE 	mandatory	}|
	{ ID 	id-SCH-Information-Cell-SetupRqstTDD				CRITICALITY		reject		TYPE	SCH-Information-Cell-SetupRqstTDD				PRESENCE	optional	}|	-- Mandatory for 3.84Mcps TDD, Not Applicable to 1.28Mcps TDD
	{ ID	id-PCCPCH-Information-Cell-SetupRqstTDD				CRITICALITY		reject		TYPE	PCCPCH-Information-Cell-SetupRqstTDD				PRESENCE	optional	}|	-- Mandatory for 3.84Mcps TDD, Not Applicable to 1.28Mcps TDD
	{ ID	id-TimeSlotConfigurationList-Cell-SetupRqstTDD		CRITICALITY		reject		TYPE 	TimeSlotConfigurationList-Cell-SetupRqstTDD		PRESENCE	optional	},	-- Mandatory for 3.84Mcps TDD, Not Applicable to 1.28Mcps TDD
	...
}

CellSetupRequestTDD-Extensions NBAP-PROTOCOL-EXTENSION ::= {
	{ ID	id-TimeSlotConfigurationList-LCR-Cell-SetupRqstTDD		CRITICALITY		reject		EXTENSION 	TimeSlotConfigurationList-LCR-Cell-SetupRqstTDD		PRESENCE	optional	}|	-- Mandatory for 1.28Mcps TDD, Not Applicable to 3.84Mcps TDD
	{ ID	id-PCCPCH-LCR-Information-Cell-SetupRqstTDD				CRITICALITY		reject		EXTENSION	PCCPCH-LCR-Information-Cell-SetupRqstTDD				PRESENCE	optional	}|	-- Mandatory for 1.28Mcps TDD, Not Applicable to 3.84Mcps TDD
	{ ID	id-DwPCH-LCR-Information-Cell-SetupRqstTDD				CRITICALITY		reject		EXTENSION	DwPCH-LCR-Information-Cell-SetupRqstTDD				PRESENCE	optional	}|	-- Mandatory for 1.28Mcps TDD, Not Applicable to 3.84Mcps TDD
	{ ID	id-ReferenceSFNoffset		CRITICALITY		ignore			EXTENSION ReferenceSFNoffset			PRESENCE	optional }|
	{ ID	id-IPDLParameter-Information-Cell-SetupRqstTDD			CRITICALITY		reject		EXTENSION		IPDLParameter-Information-Cell-SetupRqstTDD	PRESENCE	optional }|	-- Applicable to 3.84Mcps TDD only
	{ ID	id-IPDLParameter-Information-LCR-Cell-SetupRqstTDD			CRITICALITY		reject		EXTENSION		IPDLParameter-Information-LCR-Cell-SetupRqstTDD	PRESENCE	optional },	-- Applicable to 1.28Mcps TDD only
	...
}


SCH-Information-Cell-SetupRqstTDD ::= SEQUENCE {
	commonPhysicalChannelID					CommonPhysicalChannelID,
	syncCaseIndicator						SyncCaseIndicator-Cell-SetupRqstTDD-PSCH,
	sCH-Power								DL-Power,
	tSTD-Indicator							TSTD-Indicator,
	iE-Extensions							ProtocolExtensionContainer { { SCH-Information-Cell-SetupRqstTDD-ExtIEs} }		OPTIONAL,
	...
}

SCH-Information-Cell-SetupRqstTDD-ExtIEs NBAP-PROTOCOL-EXTENSION ::= {
	...
}

SyncCaseIndicator-Cell-SetupRqstTDD-PSCH ::= ProtocolIE-Single-Container {{ SyncCaseIndicatorIE-Cell-SetupRqstTDD-PSCH }}

SyncCaseIndicatorIE-Cell-SetupRqstTDD-PSCH NBAP-PROTOCOL-IES ::= {
	{ ID id-SyncCaseIndicatorItem-Cell-SetupRqstTDD-PSCH   CRITICALITY reject	TYPE SyncCaseIndicatorItem-Cell-SetupRqstTDD-PSCH		PRESENCE mandatory }
}

SyncCaseIndicatorItem-Cell-SetupRqstTDD-PSCH ::= CHOICE {
	case1								Case1-Cell-SetupRqstTDD,
	case2								Case2-Cell-SetupRqstTDD,
	...
}

Case1-Cell-SetupRqstTDD ::= SEQUENCE {
	timeSlot							TimeSlot,
	iE-Extensions						ProtocolExtensionContainer { { Case1Item-Cell-SetupRqstTDD-ExtIEs} }		OPTIONAL,
	...
}

Case1Item-Cell-SetupRqstTDD-ExtIEs NBAP-PROTOCOL-EXTENSION ::= {
	...
}

Case2-Cell-SetupRqstTDD ::= SEQUENCE {
	sCH-TimeSlot						SCH-TimeSlot,
	iE-Extensions						ProtocolExtensionContainer { { Case2Item-Cell-SetupRqstTDD-ExtIEs} }		OPTIONAL,
	...
}

Case2Item-Cell-SetupRqstTDD-ExtIEs NBAP-PROTOCOL-EXTENSION ::= {
	...
}


PCCPCH-Information-Cell-SetupRqstTDD ::= SEQUENCE {
	commonPhysicalChannelID					CommonPhysicalChannelID,
	tdd-PhysicalChannelOffset				TDD-PhysicalChannelOffset,
	repetitionPeriod						RepetitionPeriod,
	repetitionLength						RepetitionLength,
	pCCPCH-Power							PCCPCH-Power,
	sCTD-Indicator						SCTD-Indicator,
	iE-Extensions							ProtocolExtensionContainer { { PCCPCH-Information-Cell-SetupRqstTDD-ExtIEs} }		OPTIONAL,
	...
}

PCCPCH-Information-Cell-SetupRqstTDD-ExtIEs NBAP-PROTOCOL-EXTENSION ::= {
	...
}

TimeSlotConfigurationList-Cell-SetupRqstTDD ::= SEQUENCE (SIZE (1..15)) OF TimeSlotConfigurationItem-Cell-SetupRqstTDD

TimeSlotConfigurationItem-Cell-SetupRqstTDD ::= SEQUENCE {
	timeSlot								TimeSlot,
	timeSlotStatus							TimeSlotStatus,
	timeSlotDirection						TimeSlotDirection,
	iE-Extensions							ProtocolExtensionContainer { { TimeSlotConfigurationItem-Cell-SetupRqstTDD-ExtIEs} }		OPTIONAL,
	...
}

TimeSlotConfigurationItem-Cell-SetupRqstTDD-ExtIEs NBAP-PROTOCOL-EXTENSION ::= {
	...
}

TimeSlotConfigurationList-LCR-Cell-SetupRqstTDD ::= SEQUENCE (SIZE (1..7)) OF TimeSlotConfigurationItem-LCR-Cell-SetupRqstTDD

TimeSlotConfigurationItem-LCR-Cell-SetupRqstTDD ::= SEQUENCE {
	timeSlotLCR								TimeSlotLCR,
	timeSlotStatus							TimeSlotStatus,
	timeSlotDirection						TimeSlotDirection,
	iE-Extensions							ProtocolExtensionContainer { { TimeSlotConfigurationItem-LCR-Cell-SetupRqstTDD-ExtIEs} }		OPTIONAL,
	...
}

TimeSlotConfigurationItem-LCR-Cell-SetupRqstTDD-ExtIEs NBAP-PROTOCOL-EXTENSION ::= {
	...
}

PCCPCH-LCR-Information-Cell-SetupRqstTDD ::= SEQUENCE {
	commonPhysicalChannelID					CommonPhysicalChannelID,
	tdd-PhysicalChannelOffset				TDD-PhysicalChannelOffset,
	repetitionPeriod						RepetitionPeriod,
	repetitionLength						RepetitionLength,
	pCCPCH-Power							PCCPCH-Power,
	sCTD-Indicator						SCTD-Indicator,
	tSTD-Indicator							TSTD-Indicator,
	iE-Extensions							ProtocolExtensionContainer { { PCCPCH-LCR-Information-Cell-SetupRqstTDD-ExtIEs} }		OPTIONAL,
	...
}

PCCPCH-LCR-Information-Cell-SetupRqstTDD-ExtIEs NBAP-PROTOCOL-EXTENSION ::= {
	...
}

DwPCH-LCR-Information-Cell-SetupRqstTDD ::= SEQUENCE {
	commonPhysicalChannelId			CommonPhysicalChannelID,
	tSTD-Indicator					TSTD-Indicator,
	dwPCH-Power						DwPCH-Power,
	iE-Extensions					ProtocolExtensionContainer { { DwPCH-LCR-Information-Cell-SetupRqstTDD-ExtIEs} }		OPTIONAL,
	...
}

DwPCH-LCR-Information-Cell-SetupRqstTDD-ExtIEs NBAP-PROTOCOL-EXTENSION ::= {
	...
}

IPDLParameter-Information-Cell-SetupRqstTDD ::= SEQUENCE {
	iPDL-TDD-Parameters							IPDL-TDD-Parameters,
	iPDL-Indicator								IPDL-Indicator,
	iE-Extensions							ProtocolExtensionContainer { { IPDLParameter-Information-Cell-SetupRqstTDD-ExtIEs} }		OPTIONAL,
	...
}

IPDLParameter-Information-Cell-SetupRqstTDD-ExtIEs NBAP-PROTOCOL-EXTENSION ::= {
	...
}
IPDLParameter-Information-LCR-Cell-SetupRqstTDD ::= SEQUENCE {
	iPDL-TDD-Parameters-LCR					IPDL-TDD-Parameters-LCR,
	iPDL-Indicator							IPDL-Indicator,
	iE-Extensions							ProtocolExtensionContainer { { IPDLParameter-Information-LCR-Cell-SetupRqstTDD-ExtIEs} }		OPTIONAL,
	...
}

IPDLParameter-Information-LCR-Cell-SetupRqstTDD-ExtIEs NBAP-PROTOCOL-EXTENSION ::= {
	...
}

-- **************************************************************
--
-- CELL SETUP RESPONSE
--
-- **************************************************************

CellSetupResponse ::= SEQUENCE {
	protocolIEs					ProtocolIE-Container	{{CellSetupResponse-IEs}},
	protocolExtensions			ProtocolExtensionContainer	{{CellSetupResponse-Extensions}}		OPTIONAL,
	...
}

CellSetupResponse-IEs NBAP-PROTOCOL-IES ::= {
	{ ID	id-CriticalityDiagnostics		CRITICALITY		ignore			TYPE	CriticalityDiagnostics		PRESENCE	optional},
	...
}

CellSetupResponse-Extensions NBAP-PROTOCOL-EXTENSION ::= {
	...
}

-- **************************************************************
--
-- CELL SETUP FAILURE
--
-- **************************************************************

CellSetupFailure ::= SEQUENCE {
	protocolIEs				ProtocolIE-Container	{{CellSetupFailure-IEs}},
	protocolExtensions		ProtocolExtensionContainer	{{CellSetupFailure-Extensions}}			OPTIONAL,
	...
}

CellSetupFailure-IEs NBAP-PROTOCOL-IES ::= {
	{ ID	id-Cause							CRITICALITY		ignore			TYPE	Cause						PRESENCE	mandatory	}|
	{ ID	id-CriticalityDiagnostics			CRITICALITY		ignore			TYPE	CriticalityDiagnostics		PRESENCE	optional	},
	...
}

CellSetupFailure-Extensions NBAP-PROTOCOL-EXTENSION ::= {
	...
}

-- **************************************************************
--
-- CELL RECONFIGURATION REQUEST FDD
--
-- **************************************************************

CellReconfigurationRequestFDD ::= SEQUENCE {
	protocolIEs				ProtocolIE-Container	{{CellReconfigurationRequestFDD-IEs}},
	protocolExtensions		ProtocolExtensionContainer	{{CellReconfigurationRequestFDD-Extensions}} 		OPTIONAL,
	...
}

CellReconfigurationRequestFDD-IEs NBAP-PROTOCOL-IES ::= {
	{ ID	id-C-ID													CRITICALITY	reject			TYPE	C-ID												PRESENCE	mandatory	}|
	{ ID	id-ConfigurationGenerationID							CRITICALITY	reject			TYPE	ConfigurationGenerationID							PRESENCE	mandatory	}|
	{ ID	id-MaximumTransmissionPower								CRITICALITY	reject			TYPE	MaximumTransmissionPower							PRESENCE	optional	}|
	{ ID	id-Synchronisation-Configuration-Cell-ReconfRqst		CRITICALITY		reject		TYPE	Synchronisation-Configuration-Cell-ReconfRqst		PRESENCE	optional	}|
	{ ID	id-PrimarySCH-Information-Cell-ReconfRqstFDD			CRITICALITY	reject			TYPE	PrimarySCH-Information-Cell-ReconfRqstFDD			PRESENCE	optional	}|
	{ ID	id-SecondarySCH-Information-Cell-ReconfRqstFDD			CRITICALITY	reject			TYPE	SecondarySCH-Information-Cell-ReconfRqstFDD			PRESENCE	optional	}|
	{ ID	id-PrimaryCPICH-Information-Cell-ReconfRqstFDD			CRITICALITY	reject			TYPE	PrimaryCPICH-Information-Cell-ReconfRqstFDD			PRESENCE	optional	}|
	{ ID	id-SecondaryCPICH-InformationList-Cell-ReconfRqstFDD	CRITICALITY	reject			TYPE	SecondaryCPICH-InformationList-Cell-ReconfRqstFDD		PRESENCE	optional	}|
	{ ID	id-PrimaryCCPCH-Information-Cell-ReconfRqstFDD			CRITICALITY	reject			TYPE	PrimaryCCPCH-Information-Cell-ReconfRqstFDD			PRESENCE	optional	},
	...
}

CellReconfigurationRequestFDD-Extensions NBAP-PROTOCOL-EXTENSION ::= {
	{ID	id-IPDLParameter-Information-Cell-ReconfRqstFDD				CRITICALITY		reject		EXTENSION		IPDLParameter-Information-Cell-ReconfRqstFDD		PRESENCE	optional	}|
	{ID	id-PDSCH-Information-Cell-ReconfRqstFDD				CRITICALITY		reject		EXTENSION		PDSCH-Information-Cell-ReconfRqstFDD		PRESENCE	optional	},
	...
}

Synchronisation-Configuration-Cell-ReconfRqst ::= SEQUENCE {
	n-INSYNC-IND			N-INSYNC-IND,
 	n-OUTSYNC-IND			N-OUTSYNC-IND,
 	t-RLFAILURE				T-RLFAILURE,
	iE-Extensions			ProtocolExtensionContainer { { Synchronisation-Configuration-Cell-ReconfRqst-ExtIEs} }		OPTIONAL,
	...
}

Synchronisation-Configuration-Cell-ReconfRqst-ExtIEs NBAP-PROTOCOL-EXTENSION ::= {
	...
}

PrimarySCH-Information-Cell-ReconfRqstFDD ::= SEQUENCE {
 	commonPhysicalChannelID					CommonPhysicalChannelID,
 	primarySCH-Power						DL-Power,
	iE-Extensions							ProtocolExtensionContainer { { PrimarySCH-Information-Cell-ReconfRqstFDD-ExtIEs} }		OPTIONAL,
	...
 }

PrimarySCH-Information-Cell-ReconfRqstFDD-ExtIEs NBAP-PROTOCOL-EXTENSION ::= {
	...
}

SecondarySCH-Information-Cell-ReconfRqstFDD ::= SEQUENCE {
 	commonPhysicalChannelID					CommonPhysicalChannelID,
 	secondarySCH-Power						DL-Power,
	iE-Extensions							ProtocolExtensionContainer { { SecondarySCH-Information-Cell-ReconfRqstFDD-ExtIEs} }		OPTIONAL,
	...
 }

SecondarySCH-Information-Cell-ReconfRqstFDD-ExtIEs NBAP-PROTOCOL-EXTENSION ::= {
	...
}

PrimaryCPICH-Information-Cell-ReconfRqstFDD ::= SEQUENCE {
 	commonPhysicalChannelID					CommonPhysicalChannelID,
	primaryCPICH-Power						PrimaryCPICH-Power,
	iE-Extensions							ProtocolExtensionContainer { { PrimaryCPICH-Information-Cell-ReconfRqstFDD-ExtIEs} }		OPTIONAL,
	...
 }

PrimaryCPICH-Information-Cell-ReconfRqstFDD-ExtIEs NBAP-PROTOCOL-EXTENSION ::= {
	...
}

SecondaryCPICH-InformationList-Cell-ReconfRqstFDD ::= SEQUENCE (SIZE (1..maxSCPICHCell)) OF ProtocolIE-Single-Container{{ SecondaryCPICH-InformationItemIE-Cell-ReconfRqstFDD }}

SecondaryCPICH-InformationItemIE-Cell-ReconfRqstFDD NBAP-PROTOCOL-IES ::= {
	{ ID	id-SecondaryCPICH-InformationItem-Cell-ReconfRqstFDD		CRITICALITY		reject			TYPE	SecondaryCPICH-InformationItem-Cell-ReconfRqstFDD		PRESENCE	mandatory}
}

SecondaryCPICH-InformationItem-Cell-ReconfRqstFDD ::= SEQUENCE {
 	commonPhysicalChannelID						CommonPhysicalChannelID,
 	secondaryCPICH-Power						DL-Power,
	iE-Extensions								ProtocolExtensionContainer { { SecondaryCPICH-InformationItem-Cell-ReconfRqstFDD-ExtIEs} }		OPTIONAL,
	...
 }

SecondaryCPICH-InformationItem-Cell-ReconfRqstFDD-ExtIEs NBAP-PROTOCOL-EXTENSION ::= {
	...
}
 
PrimaryCCPCH-Information-Cell-ReconfRqstFDD ::= SEQUENCE {
 	bCH-information							BCH-information-Cell-ReconfRqstFDD,
	iE-Extensions							ProtocolExtensionContainer { { PrimaryCCPCH-Information-Cell-ReconfRqstFDD-ExtIEs} }		OPTIONAL,
	...
 }

PrimaryCCPCH-Information-Cell-ReconfRqstFDD-ExtIEs NBAP-PROTOCOL-EXTENSION ::= {
	...
}

BCH-information-Cell-ReconfRqstFDD ::= SEQUENCE {
 	commonTransportChannelID				CommonTransportChannelID,
 	bCH-Power								DL-Power,
	iE-Extensions							ProtocolExtensionContainer { { BCH-information-Cell-ReconfRqstFDD-ExtIEs} }		OPTIONAL,
	...
 }

BCH-information-Cell-ReconfRqstFDD-ExtIEs NBAP-PROTOCOL-EXTENSION ::= {
	...
}

IPDLParameter-Information-Cell-ReconfRqstFDD::= SEQUENCE {
	iPDL-FDD-Parameters							IPDL-FDD-Parameters		OPTIONAL,
	iPDL-Indicator								IPDL-Indicator,
	iE-Extensions							ProtocolExtensionContainer { { IPDLParameter-Information-Cell-ReconfRqstFDD-ExtIEs} }		OPTIONAL,
	...
}

IPDLParameter-Information-Cell-ReconfRqstFDD-ExtIEs NBAP-PROTOCOL-EXTENSION ::= {
	...
}

PDSCH-Information-Cell-ReconfRqstFDD	::= SEQUENCE {
	maximumPDSCH-Power			Maximum-PDSCH-Power,
	iE-Extensions				ProtocolExtensionContainer { { PDSCH-Information-Cell-ReconfRqstFDD-ExtIEs} }		OPTIONAL,
	...
}

PDSCH-Information-Cell-ReconfRqstFDD-ExtIEs NBAP-PROTOCOL-EXTENSION ::= {
	...
}

-- **************************************************************
--
-- CELL RECONFIGURATION REQUEST TDD
--
-- **************************************************************

CellReconfigurationRequestTDD ::= SEQUENCE {
	protocolIEs				ProtocolIE-Container	{{CellReconfigurationRequestTDD-IEs}},
	protocolExtensions		ProtocolExtensionContainer	{{CellReconfigurationRequestTDD-Extensions}}		OPTIONAL,
	...
}

CellReconfigurationRequestTDD-IEs NBAP-PROTOCOL-IES ::= {
	{ ID	id-C-ID												CRITICALITY		reject		TYPE	C-ID											PRESENCE	mandatory	}|
	{ ID	id-ConfigurationGenerationID						CRITICALITY		reject		TYPE	ConfigurationGenerationID						PRESENCE	mandatory	}|
	{ ID	id-Synchronisation-Configuration-Cell-ReconfRqst	CRITICALITY		reject		TYPE	Synchronisation-Configuration-Cell-ReconfRqst	PRESENCE	optional	}|
	{ ID	id-TimingAdvanceApplied								CRITICALITY		reject		TYPE	TimingAdvanceApplied							PRESENCE 	optional	}|	-- Applicable to 3.84Mcps TDD only
	{ ID	id-SCH-Information-Cell-ReconfRqstTDD				CRITICALITY		reject		TYPE	SCH-Information-Cell-ReconfRqstTDD				PRESENCE	optional	}|	-- Applicable to 3.84Mcps TDD only
	{ ID	id-PCCPCH-Information-Cell-ReconfRqstTDD			CRITICALITY		reject		TYPE	PCCPCH-Information-Cell-ReconfRqstTDD			PRESENCE	optional	}|
	{ ID	id-MaximumTransmissionPower							CRITICALITY		reject		TYPE	MaximumTransmissionPower						PRESENCE	optional	}|
	{ ID	id-DPCHConstant										CRITICALITY		reject		TYPE	ConstantValue										PRESENCE 	optional	}|
	{ ID	id-PUSCHConstant									CRITICALITY		reject		TYPE	ConstantValue										PRESENCE 		optional	}|
	{ ID	id-PRACHConstant									CRITICALITY		reject		TYPE	ConstantValue										PRESENCE 	optional	}|
	{ ID	id-TimeSlotConfigurationList-Cell-ReconfRqstTDD		CRITICALITY		reject		TYPE	TimeSlotConfigurationList-Cell-ReconfRqstTDD		PRESENCE	optional	},	-- Applicable to 3.84Mcps TDD only
	...
}

CellReconfigurationRequestTDD-Extensions NBAP-PROTOCOL-EXTENSION ::= {
	{ ID	id-TimeSlotConfigurationList-LCR-Cell-ReconfRqstTDD		CRITICALITY		reject		EXTENSION	TimeSlotConfigurationList-LCR-Cell-ReconfRqstTDD	PRESENCE optional}|	-- Mandatory for 1.28Mcps TDD, Not Applicable to 3.84Mcps TDD
	{ ID	id-DwPCH-LCR-Information-Cell-ReconfRqstTDD		CRITICALITY		reject		EXTENSION	DwPCH-LCR-Information-Cell-ReconfRqstTDD		PRESENCE optional}|	-- Mandatory for 1.28Mcps TDD, Not Applicable to 3.84Mcps TDD
	{ ID	id-IPDLParameter-Information-Cell-ReconfRqstTDD			CRITICALITY		reject		EXTENSION		IPDLParameter-Information-Cell-ReconfRqstTDD	PRESENCE	optional }|	-- Applicable to 3.84Mcps TDD only
	{ ID	id-IPDLParameter-Information-LCR-Cell-ReconfRqstTDD			CRITICALITY		reject		EXTENSION		IPDLParameter-Information-LCR-Cell-ReconfRqstTDD	PRESENCE	optional },		-- Applicable to 1.28Mcps TDD only
	...
}

SCH-Information-Cell-ReconfRqstTDD ::= SEQUENCE {
	commonPhysicalChannelID					CommonPhysicalChannelID,
	sCH-Power								DL-Power,
	iE-Extensions							ProtocolExtensionContainer { { PSCH-Information-Cell-ReconfRqstTDD-ExtIEs} }		OPTIONAL,
	...
}

PSCH-Information-Cell-ReconfRqstTDD-ExtIEs NBAP-PROTOCOL-EXTENSION ::= {
	...
}

PCCPCH-Information-Cell-ReconfRqstTDD ::= SEQUENCE {
	commonPhysicalChannelID					CommonPhysicalChannelID,
	pCCPCH-Power							PCCPCH-Power,
	iE-Extensions							ProtocolExtensionContainer { { PCCPCH-Information-Cell-ReconfRqstTDD-ExtIEs} }		OPTIONAL,
	...
}

PCCPCH-Information-Cell-ReconfRqstTDD-ExtIEs NBAP-PROTOCOL-EXTENSION ::= {
	...
}

TimeSlotConfigurationList-Cell-ReconfRqstTDD ::= SEQUENCE (SIZE (1..15)) OF TimeSlotConfigurationItem-Cell-ReconfRqstTDD

TimeSlotConfigurationItem-Cell-ReconfRqstTDD ::= SEQUENCE {
	timeSlot								TimeSlot,
 	timeSlotStatus							TimeSlotStatus,
 	timeSlotDirection						TimeSlotDirection,
	iE-Extensions							ProtocolExtensionContainer { { TimeSlotConfigurationItem-Cell-ReconfRqstTDD-ExtIEs} }		OPTIONAL,
	...
 }

TimeSlotConfigurationItem-Cell-ReconfRqstTDD-ExtIEs NBAP-PROTOCOL-EXTENSION ::= {
	...
}

TimeSlotConfigurationList-LCR-Cell-ReconfRqstTDD ::= SEQUENCE (SIZE (1..7)) OF TimeSlotConfigurationItem-LCR-Cell-ReconfRqstTDD

TimeSlotConfigurationItem-LCR-Cell-ReconfRqstTDD ::= SEQUENCE {
	timeSlotLCR								TimeSlotLCR,
 	timeSlotStatus							TimeSlotStatus,
 	timeSlotDirection						TimeSlotDirection,
	iE-Extensions							ProtocolExtensionContainer { { TimeSlotConfigurationItem-LCR-Cell-ReconfRqstTDD-ExtIEs} }		OPTIONAL,
	...
 }

TimeSlotConfigurationItem-LCR-Cell-ReconfRqstTDD-ExtIEs NBAP-PROTOCOL-EXTENSION ::= {
	...
}

DwPCH-LCR-Information-Cell-ReconfRqstTDD ::= SEQUENCE {
	commonPhysicalChannelId					CommonPhysicalChannelID,
 	dwPCH-Power								DwPCH-Power,
	iE-Extensions							ProtocolExtensionContainer { { DwPCH-LCR-Information-Cell-ReconfRqstTDD-ExtIEs} }		OPTIONAL,
	...
 }

DwPCH-LCR-Information-Cell-ReconfRqstTDD-ExtIEs NBAP-PROTOCOL-EXTENSION ::= {
	...
}

IPDLParameter-Information-Cell-ReconfRqstTDD ::= SEQUENCE {
	iPDL-TDD-Parameters							IPDL-TDD-Parameters		OPTIONAL,
	iPDL-Indicator								IPDL-Indicator,
	iE-Extensions							ProtocolExtensionContainer { { IPDLParameter-Information-Cell-ReconfRqstTDD-ExtIEs} }		OPTIONAL,
	...
}

IPDLParameter-Information-Cell-ReconfRqstTDD-ExtIEs NBAP-PROTOCOL-EXTENSION ::= {
	...
}

IPDLParameter-Information-LCR-Cell-ReconfRqstTDD ::= SEQUENCE {
	iPDL-TDD-Parameters-LCR					IPDL-TDD-Parameters-LCR		OPTIONAL,
	iPDL-Indicator							IPDL-Indicator,
	iE-Extensions							ProtocolExtensionContainer { { IPDLParameter-Information-LCR-Cell-ReconfRqstTDD-ExtIEs} }		OPTIONAL,
	...
}

IPDLParameter-Information-LCR-Cell-ReconfRqstTDD-ExtIEs NBAP-PROTOCOL-EXTENSION ::= {
	...
}

-- **************************************************************
--
-- CELL RECONFIGURATION RESPONSE
--
-- **************************************************************

CellReconfigurationResponse ::= SEQUENCE {
	protocolIEs					ProtocolIE-Container	{{CellReconfigurationResponse-IEs}},
	protocolExtensions			ProtocolExtensionContainer	{{CellReconfigurationResponse-Extensions}}		OPTIONAL,
	...
}

CellReconfigurationResponse-IEs NBAP-PROTOCOL-IES ::= {
	{ ID	id-CriticalityDiagnostics		CRITICALITY		ignore			TYPE	CriticalityDiagnostics		PRESENCE	optional},
	...
}

CellReconfigurationResponse-Extensions NBAP-PROTOCOL-EXTENSION ::= {
	...
}

-- **************************************************************
--
-- CELL RECONFIGURATION FAILURE
--
-- **************************************************************

CellReconfigurationFailure ::= SEQUENCE {
	protocolIEs				ProtocolIE-Container	{{CellReconfigurationFailure-IEs}},
	protocolExtensions		ProtocolExtensionContainer	{{CellReconfigurationFailure-Extensions}}		OPTIONAL,
	...
}

CellReconfigurationFailure-IEs NBAP-PROTOCOL-IES ::= {
	{ ID	id-Cause						CRITICALITY		ignore			TYPE	Cause							PRESENCE 	mandatory	}|
	{ ID	id-CriticalityDiagnostics		CRITICALITY		ignore			TYPE	CriticalityDiagnostics			PRESENCE	optional	},
	...
}

CellReconfigurationFailure-Extensions NBAP-PROTOCOL-EXTENSION ::= {
	...
}

-- **************************************************************
--
-- CELL DELETION REQUEST
--
-- **************************************************************

CellDeletionRequest ::= SEQUENCE {
	protocolIEs				ProtocolIE-Container	{{CellDeletionRequest-IEs}},
	protocolExtensions		ProtocolExtensionContainer	{{CellDeletionRequest-Extensions}}		OPTIONAL,
	...
}

CellDeletionRequest-IEs NBAP-PROTOCOL-IES ::= {
	{ ID	id-C-ID			CRITICALITY		reject			TYPE	C-ID		PRESENCE	mandatory},
	...
}

CellDeletionRequest-Extensions NBAP-PROTOCOL-EXTENSION ::= {
	...
}

-- **************************************************************
--
-- CELL DELETION RESPONSE
--
-- **************************************************************

CellDeletionResponse ::= SEQUENCE {
	protocolIEs				ProtocolIE-Container	{{CellDeletionResponse-IEs}},
	protocolExtensions		ProtocolExtensionContainer	{{CellDeletionResponse-Extensions}}		OPTIONAL,
	...
}

CellDeletionResponse-IEs NBAP-PROTOCOL-IES ::= {
	{ ID	id-CriticalityDiagnostics		CRITICALITY		ignore			TYPE	CriticalityDiagnostics		PRESENCE	optional},
	...
}

CellDeletionResponse-Extensions NBAP-PROTOCOL-EXTENSION ::= {
	...
}

-- **************************************************************
--
-- RESOURCE STATUS INDICATION
--
-- **************************************************************

ResourceStatusIndication ::= SEQUENCE {
	protocolIEs				ProtocolIE-Container	{{ResourceStatusIndication-IEs}},
	protocolExtensions		ProtocolExtensionContainer	{{ResourceStatusIndication-Extensions}}		OPTIONAL,
	...
}

ResourceStatusIndication-IEs NBAP-PROTOCOL-IES ::= {
	{ ID	id-IndicationType-ResourceStatusInd			CRITICALITY		ignore			TYPE	IndicationType-ResourceStatusInd		PRESENCE	mandatory	}|
	{ ID	id-Cause									CRITICALITY		ignore			TYPE	Cause									PRESENCE 	optional	},
	...
}

ResourceStatusIndication-Extensions NBAP-PROTOCOL-EXTENSION ::= {
	...
}

IndicationType-ResourceStatusInd ::= CHOICE {
	no-Failure								No-Failure-ResourceStatusInd,
	serviceImpacting						ServiceImpacting-ResourceStatusInd,
	...
}

No-Failure-ResourceStatusInd ::= SEQUENCE {
	local-Cell-InformationList				Local-Cell-InformationList-ResourceStatusInd,
	local-Cell-Group-InformationList		Local-Cell-Group-InformationList-ResourceStatusInd	OPTIONAL,
	iE-Extensions							ProtocolExtensionContainer { { No-FailureItem-ResourceStatusInd-ExtIEs} }	OPTIONAL,
	...
}

No-FailureItem-ResourceStatusInd-ExtIEs NBAP-PROTOCOL-EXTENSION ::= {
	{ ID	id-Power-Local-Cell-Group-InformationList-ResourceStatusInd		CRITICALITY		ignore			EXTENSION	Power-Local-Cell-Group-InformationList-ResourceStatusInd		PRESENCE	optional	},
	...
}

Local-Cell-InformationList-ResourceStatusInd ::= SEQUENCE(SIZE (1..maxLocalCellinNodeB)) OF ProtocolIE-Single-Container {{ Local-Cell-InformationItemIE-ResourceStatusInd }}

Local-Cell-InformationItemIE-ResourceStatusInd NBAP-PROTOCOL-IES ::= {
	{ ID id-Local-Cell-InformationItem-ResourceStatusInd   CRITICALITY ignore	TYPE Local-Cell-InformationItem-ResourceStatusInd		PRESENCE mandatory }
}

Local-Cell-InformationItem-ResourceStatusInd ::= SEQUENCE {
	local-CellID								Local-Cell-ID,
	addorDeleteIndicator						AddorDeleteIndicator,
	dl-or-global-capacityCredit					DL-or-Global-CapacityCredit		OPTIONAL,
	-- This IE shall be present if AddorDeleteIndicator IE is set to “add”
	ul-capacityCredit							UL-CapacityCredit		OPTIONAL,
	commonChannelsCapacityConsumptionLaw 		CommonChannelsCapacityConsumptionLaw	OPTIONAL,
	-- This IE shall be present if AddorDeleteIndicator IE is set to “add”
	dedicatedChannelsCapacityConsumptionLaw 	DedicatedChannelsCapacityConsumptionLaw		OPTIONAL,
	-- This IE shall be present if AddorDeleteIndicator IE is set to “add”
	maximumDL-PowerCapability					MaximumDL-PowerCapability		OPTIONAL,
	-- This IE shall be present if AddorDeleteIndicator IE is set to “add”
	minSpreadingFactor							MinSpreadingFactor					OPTIONAL,
	-- This IE shall be present if AddorDeleteIndicator IE is set to “add”
	minimumDL-PowerCapability					MinimumDL-PowerCapability		OPTIONAL,
	-- This IE shall be present if AddorDeleteIndicator IE is set to “add”
	local-Cell-Group-ID							Local-Cell-ID					OPTIONAL,
	iE-Extensions								ProtocolExtensionContainer { { Local-Cell-InformationItem-ResourceStatusInd-ExtIEs} }	OPTIONAL,
	...
}

Local-Cell-InformationItem-ResourceStatusInd-ExtIEs NBAP-PROTOCOL-EXTENSION ::= {
	{ ID	id-ReferenceClockAvailability		CRITICALITY		ignore			EXTENSION ReferenceClockAvailability			PRESENCE	optional }|
	-- This IE shall be present if AddorDeleteIndicator IE is set to “add“ and the Local Cell is related to a TDD cell
	{ ID	id-Power-Local-Cell-Group-ID		CRITICALITY		ignore			EXTENSION	Local-Cell-ID				PRESENCE	optional },
	...
}

Local-Cell-Group-InformationList-ResourceStatusInd ::= SEQUENCE(SIZE (1..maxLocalCellinNodeB)) OF ProtocolIE-Single-Container {{ Local-Cell-Group-InformationItemIE-ResourceStatusInd }}

Local-Cell-Group-InformationItemIE-ResourceStatusInd NBAP-PROTOCOL-IES ::= {
	{ ID id-Local-Cell-Group-InformationItem-ResourceStatusInd   CRITICALITY ignore	TYPE Local-Cell-Group-InformationItem-ResourceStatusInd		PRESENCE mandatory }
}

Local-Cell-Group-InformationItem-ResourceStatusInd::= SEQUENCE {
	local-Cell-Group-ID							Local-Cell-ID,
	dl-or-global-capacityCredit					DL-or-Global-CapacityCredit,
	ul-capacityCredit							UL-CapacityCredit		OPTIONAL,
	commonChannelsCapacityConsumptionLaw 		CommonChannelsCapacityConsumptionLaw,
	dedicatedChannelsCapacityConsumptionLaw 	DedicatedChannelsCapacityConsumptionLaw,
	iE-Extensions								ProtocolExtensionContainer { { Local-Cell-Group-InformationItem-ResourceStatusInd-ExtIEs} }	OPTIONAL,
	...
}

Local-Cell-Group-InformationItem-ResourceStatusInd-ExtIEs NBAP-PROTOCOL-EXTENSION ::= {
	...
}

Power-Local-Cell-Group-InformationList-ResourceStatusInd ::= SEQUENCE(SIZE (1..maxLocalCellinNodeB)) OF ProtocolIE-Single-Container {{ Power-Local-Cell-Group-InformationItemIE-ResourceStatusInd }}

Power-Local-Cell-Group-InformationItemIE-ResourceStatusInd NBAP-PROTOCOL-IES ::= {
	{ ID	id-Power-Local-Cell-Group-InformationItem-ResourceStatusInd	CRITICALITY ignore	TYPE	Power-Local-Cell-Group-InformationItem-ResourceStatusInd		PRESENCE	mandatory	}
}

Power-Local-Cell-Group-InformationItem-ResourceStatusInd::= SEQUENCE {
	power-Local-Cell-Group-ID					Local-Cell-ID,
	maximumDL-PowerCapability					MaximumDL-PowerCapability,
	iE-Extensions								ProtocolExtensionContainer { { Power-Local-Cell-Group-InformationItem-ResourceStatusInd-ExtIEs} }	OPTIONAL,
	...
}

Power-Local-Cell-Group-InformationItem-ResourceStatusInd-ExtIEs NBAP-PROTOCOL-EXTENSION ::= {
	...
}

ServiceImpacting-ResourceStatusInd ::= SEQUENCE {
	local-Cell-InformationList				Local-Cell-InformationList2-ResourceStatusInd	OPTIONAL,
	local-Cell-Group-InformationList		Local-Cell-Group-InformationList2-ResourceStatusInd	OPTIONAL,
	cCP-InformationList						CCP-InformationList-ResourceStatusInd 			OPTIONAL,
	cell-InformationList					Cell-InformationList-ResourceStatusInd 			OPTIONAL,
	iE-Extensions							ProtocolExtensionContainer { { ServiceImpactingItem-ResourceStatusInd-ExtIEs} }		OPTIONAL,
	...
}

ServiceImpactingItem-ResourceStatusInd-ExtIEs NBAP-PROTOCOL-EXTENSION ::= {
	{ ID	id-Power-Local-Cell-Group-InformationList2-ResourceStatusInd		CRITICALITY		ignore			EXTENSION	Power-Local-Cell-Group-InformationList2-ResourceStatusInd		PRESENCE	optional	},
	...
}

Local-Cell-InformationList2-ResourceStatusInd ::= SEQUENCE(SIZE (1..maxLocalCellinNodeB)) OF ProtocolIE-Single-Container {{ Local-Cell-InformationItemIE2-ResourceStatusInd }}

Local-Cell-InformationItemIE2-ResourceStatusInd NBAP-PROTOCOL-IES ::= {
	{ ID id-Local-Cell-InformationItem2-ResourceStatusInd   CRITICALITY ignore	TYPE Local-Cell-InformationItem2-ResourceStatusInd		PRESENCE mandatory }
}

Local-Cell-InformationItem2-ResourceStatusInd ::= SEQUENCE {
	local-Cell-ID							Local-Cell-ID,
	dl-or-global-capacityCredit				DL-or-Global-CapacityCredit		OPTIONAL,
	ul-capacityCredit						UL-CapacityCredit				OPTIONAL,
	commonChannelsCapacityConsumptionLaw 		CommonChannelsCapacityConsumptionLaw	OPTIONAL,
	dedicatedChannelsCapacityConsumptionLaw 	DedicatedChannelsCapacityConsumptionLaw	OPTIONAL,
	maximum-DL-PowerCapability				MaximumDL-PowerCapability		OPTIONAL,
	minSpreadingFactor						MinSpreadingFactor				OPTIONAL,
	minimumDL-PowerCapability				MinimumDL-PowerCapability		OPTIONAL,
	iE-Extensions							ProtocolExtensionContainer { { Local-Cell-InformationItem2-ResourceStatusInd-ExtIEs} }		OPTIONAL,
	...
}

Local-Cell-InformationItem2-ResourceStatusInd-ExtIEs NBAP-PROTOCOL-EXTENSION ::= {
	{ ID	id-ReferenceClockAvailability		CRITICALITY		ignore			EXTENSION ReferenceClockAvailability			PRESENCE	optional }|
	{ ID	id-Power-Local-Cell-Group-ID		CRITICALITY		ignore			EXTENSION	Local-Cell-ID				PRESENCE	optional },
	...
}

Local-Cell-Group-InformationList2-ResourceStatusInd ::= SEQUENCE(SIZE (1..maxLocalCellinNodeB)) OF ProtocolIE-Single-Container {{ Local-Cell-Group-InformationItemIE2-ResourceStatusInd }}

Local-Cell-Group-InformationItemIE2-ResourceStatusInd NBAP-PROTOCOL-IES ::= {
	{ ID id-Local-Cell-Group-InformationItem2-ResourceStatusInd   CRITICALITY ignore	TYPE Local-Cell-Group-InformationItem2-ResourceStatusInd		PRESENCE mandatory }
}

Local-Cell-Group-InformationItem2-ResourceStatusInd ::= SEQUENCE {
	local-Cell-Group-ID						Local-Cell-ID,
	dl-or-global-capacityCredit				DL-or-Global-CapacityCredit		OPTIONAL,
	ul-capacityCredit						UL-CapacityCredit				OPTIONAL,
	commonChannelsCapacityConsumptionLaw 		CommonChannelsCapacityConsumptionLaw	OPTIONAL,
	dedicatedChannelsCapacityConsumptionLaw 	DedicatedChannelsCapacityConsumptionLaw	OPTIONAL,
	iE-Extensions							ProtocolExtensionContainer { { Local-Cell-Group-InformationItem2-ResourceStatusInd-ExtIEs} }		OPTIONAL,
	...
}

Local-Cell-Group-InformationItem2-ResourceStatusInd-ExtIEs NBAP-PROTOCOL-EXTENSION ::= {
	...
}

Power-Local-Cell-Group-InformationList2-ResourceStatusInd ::= SEQUENCE(SIZE (1..maxLocalCellinNodeB)) OF ProtocolIE-Single-Container {{ Power-Local-Cell-Group-InformationItemIE2-ResourceStatusInd }}

Power-Local-Cell-Group-InformationItemIE2-ResourceStatusInd NBAP-PROTOCOL-IES ::= {
	{ ID	id-Power-Local-Cell-Group-InformationItem2-ResourceStatusInd	CRITICALITY ignore	TYPE	Power-Local-Cell-Group-InformationItem2-ResourceStatusInd		PRESENCE	mandatory	}
}

Power-Local-Cell-Group-InformationItem2-ResourceStatusInd::= SEQUENCE {
	power-Local-Cell-Group-ID					Local-Cell-ID,
	maximumDL-PowerCapability					MaximumDL-PowerCapability,
	iE-Extensions								ProtocolExtensionContainer { { Power-Local-Cell-Group-InformationItem2-ResourceStatusInd-ExtIEs} }	OPTIONAL,
	...
}

Power-Local-Cell-Group-InformationItem2-ResourceStatusInd-ExtIEs NBAP-PROTOCOL-EXTENSION ::= {
	...
}

CCP-InformationList-ResourceStatusInd ::= SEQUENCE (SIZE (1..maxCCPinNodeB)) OF ProtocolIE-Single-Container {{ CCP-InformationItemIE-ResourceStatusInd }}

CCP-InformationItemIE-ResourceStatusInd NBAP-PROTOCOL-IES ::= {
	{ ID id-CCP-InformationItem-ResourceStatusInd   CRITICALITY ignore	TYPE CCP-InformationItem-ResourceStatusInd		PRESENCE mandatory }
}

CCP-InformationItem-ResourceStatusInd ::= SEQUENCE {
	communicationControlPortID				CommunicationControlPortID,
	resourceOperationalState				ResourceOperationalState,
	availabilityStatus						AvailabilityStatus,
	iE-Extensions							ProtocolExtensionContainer { { CCP-InformationItem-ResourceStatusInd-ExtIEs} }		OPTIONAL,
	...
}

CCP-InformationItem-ResourceStatusInd-ExtIEs NBAP-PROTOCOL-EXTENSION ::= {
	...
}

Cell-InformationList-ResourceStatusInd ::= SEQUENCE (SIZE (1..maxCellinNodeB)) OF ProtocolIE-Single-Container {{ Cell-InformationItemIE-ResourceStatusInd }}

Cell-InformationItemIE-ResourceStatusInd NBAP-PROTOCOL-IES ::= {
	{ ID id-Cell-InformationItem-ResourceStatusInd   CRITICALITY ignore	TYPE Cell-InformationItem-ResourceStatusInd		PRESENCE mandatory }
}

Cell-InformationItem-ResourceStatusInd  ::= SEQUENCE {
	c-ID									C-ID,
	resourceOperationalState 				ResourceOperationalState						OPTIONAL,
	availabilityStatus						AvailabilityStatus								OPTIONAL,
	primary-SCH-Information					P-SCH-Information-ResourceStatusInd				OPTIONAL, -- FDD only
	secondary-SCH-Information				S-SCH-Information-ResourceStatusInd				OPTIONAL, -- FDD only
	primary-CPICH-Information				P-CPICH-Information-ResourceStatusInd			OPTIONAL, -- FDD only
	secondary-CPICH-Information				S-CPICH-InformationList-ResourceStatusInd		OPTIONAL, -- FDD only
	primary-CCPCH-Information				P-CCPCH-Information-ResourceStatusInd			OPTIONAL,
	bCH-Information							BCH-Information-ResourceStatusInd 				OPTIONAL,
	secondary-CCPCH-InformationList			S-CCPCH-InformationList-ResourceStatusInd		OPTIONAL,
	pCH-Information							PCH-Information-ResourceStatusInd 				OPTIONAL,
	pICH-Information						PICH-Information-ResourceStatusInd				OPTIONAL,
	fACH-InformationList					FACH-InformationList-ResourceStatusInd 			OPTIONAL,
	pRACH-InformationList					PRACH-InformationList-ResourceStatusInd			OPTIONAL,
	rACH-InformationList					RACH-InformationList-ResourceStatusInd 			OPTIONAL,
	aICH-InformationList					AICH-InformationList-ResourceStatusInd 			OPTIONAL, -- FDD only
	pCPCH-InformationList					PCPCH-InformationList-ResourceStatusInd			OPTIONAL, -- FDD only
	cPCH-InformationList					CPCH-InformationList-ResourceStatusInd 			OPTIONAL, -- FDD only
	aP-AICH-InformationList					AP-AICH-InformationList-ResourceStatusInd 		OPTIONAL, -- FDD only
	cDCA-ICH-InformationList				CDCA-ICH-InformationList-ResourceStatusInd 		OPTIONAL, -- FDD only
	sCH-Information							SCH-Information-ResourceStatusInd 				OPTIONAL, -- Applicable to 3.84Mcps TDD only
	iE-Extensions							ProtocolExtensionContainer { { Cell-InformationItem-ResourceStatusInd-ExtIEs} }	OPTIONAL,
	...
}

Cell-InformationItem-ResourceStatusInd-ExtIEs NBAP-PROTOCOL-EXTENSION ::= {
	{ ID id-FPACH-LCR-InformationList-ResourceStatusInd		CRITICALITY ignore		EXTENSION	FPACH-LCR-InformationList-ResourceStatusInd			PRESENCE optional	}|	-- Applicable to 1.28Mcps TDD only
	{ ID id-DwPCH-LCR-Information-ResourceStatusInd			CRITICALITY ignore		EXTENSION 	DwPCH-LCR-Information-ResourceStatusInd			PRESENCE optional	},	-- Applicable to 1.28Mcps TDD only
	...
}

P-SCH-Information-ResourceStatusInd ::= ProtocolIE-Single-Container {{ P-SCH-InformationIE-ResourceStatusInd }}

P-SCH-InformationIE-ResourceStatusInd NBAP-PROTOCOL-IES ::= {
	{ ID id-P-SCH-Information   CRITICALITY ignore	TYPE Common-PhysicalChannel-Status-Information		PRESENCE mandatory }
}

S-SCH-Information-ResourceStatusInd ::= ProtocolIE-Single-Container {{ S-SCH-InformationIE-ResourceStatusInd }}

S-SCH-InformationIE-ResourceStatusInd NBAP-PROTOCOL-IES ::= {
	{ ID id-S-SCH-Information   CRITICALITY ignore	TYPE Common-PhysicalChannel-Status-Information		PRESENCE mandatory }
}

P-CPICH-Information-ResourceStatusInd ::= ProtocolIE-Single-Container {{ P-CPICH-InformationIE-ResourceStatusInd }}

P-CPICH-InformationIE-ResourceStatusInd NBAP-PROTOCOL-IES ::= {
	{ ID id-P-CPICH-Information   CRITICALITY ignore	TYPE Common-PhysicalChannel-Status-Information		PRESENCE mandatory }
}

S-CPICH-InformationList-ResourceStatusInd ::= SEQUENCE (SIZE (1..maxSCPICHCell)) OF ProtocolIE-Single-Container {{ S-CPICH-InformationItemIE-ResourceStatusInd }}

S-CPICH-InformationItemIE-ResourceStatusInd NBAP-PROTOCOL-IES ::= {
	{ ID id-S-CPICH-Information   CRITICALITY ignore	TYPE Common-PhysicalChannel-Status-Information		PRESENCE mandatory }
}

P-CCPCH-Information-ResourceStatusInd ::= ProtocolIE-Single-Container {{ P-CCPCH-InformationIE-ResourceStatusInd }}

P-CCPCH-InformationIE-ResourceStatusInd NBAP-PROTOCOL-IES ::= {
	{ ID id-P-CCPCH-Information   CRITICALITY ignore	TYPE Common-PhysicalChannel-Status-Information		PRESENCE mandatory }
}

BCH-Information-ResourceStatusInd ::= ProtocolIE-Single-Container {{ BCH-InformationIE-ResourceStatusInd }}

BCH-InformationIE-ResourceStatusInd NBAP-PROTOCOL-IES ::= {
	{ ID id-BCH-Information   CRITICALITY ignore	TYPE Common-TransportChannel-Status-Information		PRESENCE mandatory }
}

S-CCPCH-InformationList-ResourceStatusInd ::= SEQUENCE (SIZE (1..maxSCCPCHCell)) OF ProtocolIE-Single-Container {{ S-CCPCH-InformationItemIE-ResourceStatusInd }}

S-CCPCH-InformationItemIE-ResourceStatusInd NBAP-PROTOCOL-IES ::= {
	{ ID id-S-CCPCH-Information   CRITICALITY ignore	TYPE Common-PhysicalChannel-Status-Information		PRESENCE mandatory }
}

PCH-Information-ResourceStatusInd ::= ProtocolIE-Single-Container {{ PCH-InformationIE-ResourceStatusInd }}

PCH-InformationIE-ResourceStatusInd NBAP-PROTOCOL-IES ::= {
	{ ID id-PCH-Information   CRITICALITY ignore	TYPE Common-TransportChannel-Status-Information		PRESENCE mandatory }
}

PICH-Information-ResourceStatusInd ::= ProtocolIE-Single-Container {{ PICH-InformationIE-ResourceStatusInd }}

PICH-InformationIE-ResourceStatusInd NBAP-PROTOCOL-IES ::= {
	{ ID id-PICH-Information   CRITICALITY ignore	TYPE Common-PhysicalChannel-Status-Information		PRESENCE mandatory }
}

FACH-InformationList-ResourceStatusInd ::= SEQUENCE (SIZE (1..maxFACHCell)) OF ProtocolIE-Single-Container {{ FACH-InformationItemIE-ResourceStatusInd }}

FACH-InformationItemIE-ResourceStatusInd NBAP-PROTOCOL-IES ::= {
	{ ID id-FACH-Information   CRITICALITY ignore	TYPE Common-TransportChannel-Status-Information		PRESENCE mandatory }
}

PRACH-InformationList-ResourceStatusInd ::= SEQUENCE (SIZE (1..maxPRACHCell)) OF ProtocolIE-Single-Container {{ PRACH-InformationItemIE-ResourceStatusInd }}

PRACH-InformationItemIE-ResourceStatusInd NBAP-PROTOCOL-IES ::= {
	{ ID id-PRACH-Information   CRITICALITY ignore	TYPE Common-PhysicalChannel-Status-Information		PRESENCE mandatory }
}

RACH-InformationList-ResourceStatusInd ::= SEQUENCE (SIZE (1..maxPRACHCell)) OF ProtocolIE-Single-Container {{ RACH-InformationItemIE-ResourceStatusInd }}

RACH-InformationItemIE-ResourceStatusInd NBAP-PROTOCOL-IES ::= {
	{ ID id-RACH-Information   CRITICALITY ignore	TYPE Common-TransportChannel-Status-Information		PRESENCE mandatory }
}

AICH-InformationList-ResourceStatusInd ::= SEQUENCE (SIZE (1..maxPRACHCell)) OF ProtocolIE-Single-Container {{ AICH-InformationItemIE-ResourceStatusInd }}

AICH-InformationItemIE-ResourceStatusInd NBAP-PROTOCOL-IES ::= {
	{ ID id-AICH-Information   CRITICALITY ignore	TYPE Common-PhysicalChannel-Status-Information		PRESENCE mandatory }
}

PCPCH-InformationList-ResourceStatusInd ::= SEQUENCE (SIZE (1..maxPCPCHCell)) OF ProtocolIE-Single-Container {{ PCPCH-InformationItemIE-ResourceStatusInd }}

PCPCH-InformationItemIE-ResourceStatusInd NBAP-PROTOCOL-IES ::= {
	{ ID id-PCPCH-Information   CRITICALITY ignore	TYPE Common-PhysicalChannel-Status-Information		PRESENCE optional }
}

CPCH-InformationList-ResourceStatusInd ::= SEQUENCE (SIZE (1..maxCPCHCell)) OF ProtocolIE-Single-Container {{ CPCH-InformationItemIE-ResourceStatusInd }}

CPCH-InformationItemIE-ResourceStatusInd NBAP-PROTOCOL-IES ::= {
	{ ID id-CPCH-Information   CRITICALITY ignore	TYPE Common-TransportChannel-Status-Information		PRESENCE optional }
}

AP-AICH-InformationList-ResourceStatusInd ::= SEQUENCE (SIZE (1..maxCPCHCell)) OF ProtocolIE-Single-Container {{ AP-AICH-InformationItemIE-ResourceStatusInd }}

AP-AICH-InformationItemIE-ResourceStatusInd NBAP-PROTOCOL-IES ::= {
	{ ID id-AP-AICH-Information   CRITICALITY ignore	TYPE Common-PhysicalChannel-Status-Information		PRESENCE optional }
}

CDCA-ICH-InformationList-ResourceStatusInd ::= SEQUENCE (SIZE (1..maxCPCHCell)) OF ProtocolIE-Single-Container {{ CDCA-ICH-InformationItemIE-ResourceStatusInd }}

CDCA-ICH-InformationItemIE-ResourceStatusInd NBAP-PROTOCOL-IES ::= {
	{ ID id-CDCA-ICH-Information   CRITICALITY ignore	TYPE Common-PhysicalChannel-Status-Information		PRESENCE optional }
}

SCH-Information-ResourceStatusInd ::= ProtocolIE-Single-Container {{ SCH-InformationIE-ResourceStatusInd }}

SCH-InformationIE-ResourceStatusInd NBAP-PROTOCOL-IES ::= {
	{ ID id-SCH-Information   CRITICALITY ignore	TYPE Common-PhysicalChannel-Status-Information		PRESENCE mandatory }
}

FPACH-LCR-InformationList-ResourceStatusInd ::= SEQUENCE (SIZE (1..maxFPACHCell)) OF ProtocolIE-Single-Container {{ FPACH-LCR-InformationItemIE-ResourceStatusInd }}

FPACH-LCR-InformationItemIE-ResourceStatusInd NBAP-PROTOCOL-IES ::= {
	{ ID id-FPACH-LCR-Information  CRITICALITY ignore	TYPE Common-PhysicalChannel-Status-Information		PRESENCE mandatory }
}

DwPCH-LCR-Information-ResourceStatusInd ::= ProtocolIE-Single-Container {{ DwPCH-LCR-InformationIE-ResourceStatusInd }}

DwPCH-LCR-InformationIE-ResourceStatusInd NBAP-PROTOCOL-IES ::= {
	{ ID id-DwPCH-LCR-Information   CRITICALITY ignore	TYPE Common-PhysicalChannel-Status-Information		PRESENCE mandatory }
}

-- **************************************************************
--
-- SYSTEM INFORMATION UPDATE REQUEST
--
-- **************************************************************

SystemInformationUpdateRequest ::= SEQUENCE {
	protocolIEs				ProtocolIE-Container	{{SystemInformationUpdateRequest-IEs}},
	protocolExtensions		ProtocolExtensionContainer	{{SystemInformationUpdateRequest-Extensions}}		OPTIONAL,
	...
}

SystemInformationUpdateRequest-IEs NBAP-PROTOCOL-IES ::= {
	{ ID	id-C-ID												CRITICALITY	reject		TYPE	C-ID											PRESENCE mandatory	}|
	{ ID 	id-BCCH-ModificationTime							CRITICALITY	reject		TYPE	BCCH-ModificationTime					PRESENCE	optional	}|
	{ ID	id-MIB-SB-SIB-InformationList-SystemInfoUpdateRqst		CRITICALITY	reject		TYPE	MIB-SB-SIB-InformationList-SystemInfoUpdateRqst		PRESENCE 	mandatory	},
	...
}

SystemInformationUpdateRequest-Extensions NBAP-PROTOCOL-EXTENSION ::= {
	...
}

MIB-SB-SIB-InformationList-SystemInfoUpdateRqst ::= SEQUENCE (SIZE (1..maxIB)) OF MIB-SB-SIB-InformationItem-SystemInfoUpdateRqst

MIB-SB-SIB-InformationItem-SystemInfoUpdateRqst ::= SEQUENCE {
	iB-Type								IB-Type,	
	iB-OC-ID							IB-OC-ID,
	deletionIndicator					DeletionIndicator-SystemInfoUpdate,
	iE-Extensions						ProtocolExtensionContainer { { MIB-SB-SIB-InformationItem-SystemInfoUpdateRqst-ExtIEs} }		OPTIONAL,
	...
}

MIB-SB-SIB-InformationItem-SystemInfoUpdateRqst-ExtIEs NBAP-PROTOCOL-EXTENSION ::= {
	...
}

DeletionIndicator-SystemInfoUpdate ::= CHOICE {
	no-Deletion							No-Deletion-SystemInfoUpdate,
	yes-Deletion						NULL

}

No-Deletion-SystemInfoUpdate ::= SEQUENCE {
	sIB-Originator							SIB-Originator				OPTIONAL,
	-- This IE shall be present if the IB-Type IE is set to "SIB"
	iB-SG-REP								IB-SG-REP					OPTIONAL,
	segmentInformationList					SegmentInformationList-SystemInfoUpdate,
	iE-Extensions							ProtocolExtensionContainer { { No-DeletionItem-SystemInfoUpdate-ExtIEs} }		OPTIONAL,
	...
}

No-DeletionItem-SystemInfoUpdate-ExtIEs NBAP-PROTOCOL-EXTENSION ::= {
	...
}

SegmentInformationList-SystemInfoUpdate ::= ProtocolIE-Single-Container {{ SegmentInformationListIEs-SystemInfoUpdate }}

SegmentInformationListIEs-SystemInfoUpdate NBAP-PROTOCOL-IES ::= {
	{ ID id-SegmentInformationListIE-SystemInfoUpdate   CRITICALITY reject	TYPE SegmentInformationListIE-SystemInfoUpdate		PRESENCE mandatory }
}

SegmentInformationListIE-SystemInfoUpdate ::= SEQUENCE (SIZE (1..maxIBSEG)) OF SegmentInformationItem-SystemInfoUpdate

SegmentInformationItem-SystemInfoUpdate ::= SEQUENCE {
	iB-SG-POS								IB-SG-POS			OPTIONAL,
	segment-Type							Segment-Type		OPTIONAL,
	-- This IE shall be present if the SIB Originator IE is set to "CRNC" or the IB-Type IE is set to "MIB", "SB1" or "SB2"
	iB-SG-DATA								IB-SG-DATA			OPTIONAL,
	-- This IE shall be present if the SIB Originator IE is set to "CRNC" or the IB-Type IE is set to "MIB", "SB1" or "SB2"
	iE-Extensions							ProtocolExtensionContainer { { SegmentInformationItem-SystemInfoUpdate-ExtIEs} }	OPTIONAL,
	...
}

SegmentInformationItem-SystemInfoUpdate-ExtIEs NBAP-PROTOCOL-EXTENSION ::= {
	...
}

-- **************************************************************
--
-- SYSTEM INFORMATION UPDATE RESPONSE
--
-- **************************************************************

SystemInformationUpdateResponse ::= SEQUENCE {
	protocolIEs				ProtocolIE-Container    {{SystemInformationUpdateResponse-IEs}},
	protocolExtensions		ProtocolExtensionContainer	{{SystemInformationUpdateResponse-Extensions}}		OPTIONAL,
	...
}

SystemInformationUpdateResponse-IEs NBAP-PROTOCOL-IES ::= {
	{ ID	id-CriticalityDiagnostics		CRITICALITY		ignore			TYPE	CriticalityDiagnostics		PRESENCE	optional},
	...
}

SystemInformationUpdateResponse-Extensions NBAP-PROTOCOL-EXTENSION ::= {
	...
}

-- **************************************************************
--
-- SYSTEM INFORMATION UPDATE FAILURE
--
-- **************************************************************

SystemInformationUpdateFailure ::= SEQUENCE {
	protocolIEs				ProtocolIE-Container	{{SystemInformationUpdateFailure-IEs}},
	protocolExtensions		ProtocolExtensionContainer	{{SystemInformationUpdateFailure-Extensions}}		OPTIONAL,
	...
}

SystemInformationUpdateFailure-IEs NBAP-PROTOCOL-IES ::= {
	{ ID	id-Cause							CRITICALITY		ignore			TYPE	Cause						PRESENCE	mandatory	}|
	{ ID 	id-CriticalityDiagnostics			CRITICALITY		ignore			TYPE	CriticalityDiagnostics		PRESENCE	optional	},
	...
}

SystemInformationUpdateFailure-Extensions NBAP-PROTOCOL-EXTENSION ::= {
	...
}

-- **************************************************************
--
-- RADIO LINK SETUP REQUEST FDD
--
-- **************************************************************

RadioLinkSetupRequestFDD ::= SEQUENCE {
	protocolIEs				ProtocolIE-Container	{{RadioLinkSetupRequestFDD-IEs}},
	protocolExtensions		ProtocolExtensionContainer	{{RadioLinkSetupRequestFDD-Extensions}}			OPTIONAL,
	...
}

RadioLinkSetupRequestFDD-IEs NBAP-PROTOCOL-IES ::= {
	{ ID	id-CRNC-CommunicationContextID					CRITICALITY	reject				TYPE	CRNC-CommunicationContextID					PRESENCE	mandatory	}|
	{ ID	id-UL-DPCH-Information-RL-SetupRqstFDD			CRITICALITY	reject				TYPE	UL-DPCH-Information-RL-SetupRqstFDD			PRESENCE	mandatory	}|
	{ ID	id-DL-DPCH-Information-RL-SetupRqstFDD			CRITICALITY	reject				TYPE	DL-DPCH-Information-RL-SetupRqstFDD			PRESENCE	mandatory	}|
	{ ID	id-DCH-FDD-Information			CRITICALITY	reject				TYPE	DCH-FDD-Information			PRESENCE	mandatory	}|
	{ ID	id-DSCH-FDD-Information			CRITICALITY	reject				TYPE	DSCH-FDD-Information		PRESENCE	optional	}|
	{ ID	id-TFCI2-Bearer-Information-RL-SetupRqstFDD		CRITICALITY	ignore				TYPE	TFCI2-Bearer-Information-RL-SetupRqstFDD	PRESENCE	optional	}|
	{ ID	id-RL-InformationList-RL-SetupRqstFDD			CRITICALITY	notify				TYPE	RL-InformationList-RL-SetupRqstFDD			PRESENCE	mandatory	}|
	{ ID id-Transmission-Gap-Pattern-Sequence-Information		CRITICALITY reject				TYPE Transmission-Gap-Pattern-Sequence-Information	 PRESENCE optional } |
{ ID id-Active-Pattern-Sequence-Information				CRITICALITY reject				TYPE Active-Pattern-Sequence-Information	 PRESENCE optional },
	...
}

RadioLinkSetupRequestFDD-Extensions NBAP-PROTOCOL-EXTENSION ::= {
	{ ID id-DSCH-FDD-Common-Information					CRITICALITY ignore	EXTENSION DSCH-FDD-Common-Information						PRESENCE optional	}|
	{ ID id-DL-PowerBalancing-Information		CRITICALITY ignore		EXTENSION	DL-PowerBalancing-Information		PRESENCE optional}|
	{ ID id-HSDSCH-FDD-Information					CRITICALITY reject	EXTENSION HSDSCH-FDD-Information		PRESENCE optional	}|
	{ ID id-HSDSCH-RNTI								CRITICALITY reject	EXTENSION HSDSCH-RNTI			PRESENCE conditional	}|
	-- The IE shall be present if HS-DSCH Information IE is present
	{ ID id-HSPDSCH-RL-ID							CRITICALITY reject	EXTENSION RL-ID					PRESENCE conditional	},
	-- The IE shall be present if HS-DSCH Information IE is present
	...
}

UL-DPCH-Information-RL-SetupRqstFDD ::= SEQUENCE {
	ul-ScramblingCode						UL-ScramblingCode,
	minUL-ChannelisationCodeLength			MinUL-ChannelisationCodeLength,
	maxNrOfUL-DPDCHs						MaxNrOfUL-DPDCHs		OPTIONAL,
	-- This IE shall be present if Min UL Channelisation Code length IE is set to 4 --
	ul-PunctureLimit						PunctureLimit,
	tFCS									TFCS,
	ul-DPCCH-SlotFormat						UL-DPCCH-SlotFormat,
	ul-SIR-Target							UL-SIR,
	diversityMode							DiversityMode,
	sSDT-CellID-Length						SSDT-CellID-Length		OPTIONAL,
	s-FieldLength							S-FieldLength			OPTIONAL,
	iE-Extensions							ProtocolExtensionContainer { { UL-DPCH-Information-RL-SetupRqstFDD-ExtIEs} }	OPTIONAL,
	...
}

UL-DPCH-Information-RL-SetupRqstFDD-ExtIEs NBAP-PROTOCOL-EXTENSION ::= {
	{ID id-DPC-Mode			CRITICALITY reject	EXTENSION 	DPC-Mode 	PRESENCE optional	},
	...
}

DL-DPCH-Information-RL-SetupRqstFDD ::= SEQUENCE {
	tFCS									TFCS,
	dl-DPCH-SlotFormat						DL-DPCH-SlotFormat,
	tFCI-SignallingMode						TFCI-SignallingMode,
	tFCI-Presence							TFCI-Presence	OPTIONAL,
	-- this IE shall be present if the DL DPCH slot format IE is set to any of the values from 12 to 16 --	
	multiplexingPosition					MultiplexingPosition,
	pDSCH-RL-ID								RL-ID			OPTIONAL,
	-- This IE shall be present if the DSCH Information IE is present --
	pDSCH-CodeMapping						PDSCH-CodeMapping		OPTIONAL,
	-- This IE shall be present if the DSCH Information IE is present --
	powerOffsetInformation					PowerOffsetInformation-RL-SetupRqstFDD,
	fdd-TPC-DownlinkStepSize				FDD-TPC-DownlinkStepSize,
	limitedPowerIncrease					LimitedPowerIncrease,
	innerLoopDLPCStatus						InnerLoopDLPCStatus,
	iE-Extensions							ProtocolExtensionContainer { { DL-DPCH-Information-RL-SetupRqstFDD-ExtIEs} }	OPTIONAL,
	...
}

DL-DPCH-Information-RL-SetupRqstFDD-ExtIEs NBAP-PROTOCOL-EXTENSION ::= {
	...
}

PowerOffsetInformation-RL-SetupRqstFDD ::= SEQUENCE {
	pO1-ForTFCI-Bits						PowerOffset,
	pO2-ForTPC-Bits							PowerOffset,
	pO3-ForPilotBits						PowerOffset,
	iE-Extensions							ProtocolExtensionContainer { { PowerOffsetInformation-RL-SetupRqstFDD-ExtIEs} }	OPTIONAL,
	...
}

PowerOffsetInformation-RL-SetupRqstFDD-ExtIEs NBAP-PROTOCOL-EXTENSION ::= {
	...
}

TFCI2-Bearer-Information-RL-SetupRqstFDD ::= SEQUENCE {
	toAWS								ToAWS,
	toAWE								ToAWE,
	iE-Extensions						ProtocolExtensionContainer { { TFCI2-Bearer-Information-RL-SetupRqstFDD-ExtIEs} }		OPTIONAL,
	...
}

TFCI2-Bearer-Information-RL-SetupRqstFDD-ExtIEs NBAP-PROTOCOL-EXTENSION ::= {
	{ ID id-bindingID						CRITICALITY	ignore		EXTENSION 	BindingID			PRESENCE 	optional	}|
	{ ID id-transportlayeraddress			CRITICALITY	ignore		EXTENSION 	TransportLayerAddress	PRESENCE 	optional	},
	...
}

RL-InformationList-RL-SetupRqstFDD ::= SEQUENCE (SIZE (1..maxNrOfRLs)) OF
	ProtocolIE-Single-Container{{ RL-InformationItemIE-RL-SetupRqstFDD }}

RL-InformationItemIE-RL-SetupRqstFDD NBAP-PROTOCOL-IES ::= {
	{ ID	id-RL-InformationItem-RL-SetupRqstFDD			CRITICALITY		notify			TYPE	RL-InformationItem-RL-SetupRqstFDD		PRESENCE	mandatory}
}

RL-InformationItem-RL-SetupRqstFDD ::= SEQUENCE {
	rL-ID								RL-ID,
	c-ID								C-ID,
	firstRLS-indicator					FirstRLS-Indicator,
	frameOffset							FrameOffset,
	chipOffset							ChipOffset,
	propagationDelay					PropagationDelay			OPTIONAL,
	diversityControlField				DiversityControlField		OPTIONAL,
	-- This IE shall be present if the RL is not the first one in the RL Information IE
	dl-CodeInformation					FDD-DL-CodeInformation,
	initialDL-transmissionPower			DL-Power,
	maximumDL-power						DL-Power,
	minimumDL-power						DL-Power,
	sSDT-Cell-Identity					SSDT-Cell-Identity			OPTIONAL,
	transmitDiversityIndicator			TransmitDiversityIndicator		OPTIONAL,
	-- This IE shall be present if Diversity Mode IE in UL DPCH Information group is not set to “none”
	iE-Extensions						ProtocolExtensionContainer { { RL-InformationItem-RL-SetupRqstFDD-ExtIEs} }		OPTIONAL,
	...
}

RL-InformationItem-RL-SetupRqstFDD-ExtIEs NBAP-PROTOCOL-EXTENSION ::= {
	{ ID id-SSDT-CellIDforEDSCHPC CRITICALITY ignore EXTENSION SSDT-Cell-Identity 		PRESENCE conditional }|
	-- This IE shall be present if Enhanced DSCH PC IE is present in the DSCH Common Information IE.
	{ ID id-RL-Specific-DCH-Info	CRITICALITY	ignore		EXTENSION 	RL-Specific-DCH-Info	PRESENCE 	optional	}|
	{ ID id-DelayedActivation CRITICALITY reject EXTENSION DelayedActivation PRESENCE optional }|
	{ ID id-Qth-Parameter	CRITICALITY ignore		EXTENSION	Qth-Parameter 		PRESENCE optional },
	...
}

-- **************************************************************
--
-- RADIO LINK SETUP REQUEST TDD
--
-- **************************************************************

RadioLinkSetupRequestTDD ::= SEQUENCE {
	protocolIEs				ProtocolIE-Container	{{RadioLinkSetupRequestTDD-IEs}},
	protocolExtensions		ProtocolExtensionContainer	{{RadioLinkSetupRequestTDD-Extensions}}		OPTIONAL,
	...
}

RadioLinkSetupRequestTDD-IEs NBAP-PROTOCOL-IES ::= {
	{ ID	id-CRNC-CommunicationContextID						CRITICALITY	reject			TYPE	CRNC-CommunicationContextID						PRESENCE	mandatory	}|
	{ ID	id-UL-CCTrCH-InformationList-RL-SetupRqstTDD		CRITICALITY	notify			TYPE	UL-CCTrCH-InformationList-RL-SetupRqstTDD		PRESENCE	optional	}|
	{ ID	id-DL-CCTrCH-InformationList-RL-SetupRqstTDD 		CRITICALITY	notify			TYPE	DL-CCTrCH-InformationList-RL-SetupRqstTDD		PRESENCE	optional	}|
	{ ID	id-DCH-TDD-Information				CRITICALITY	reject			TYPE	DCH-TDD-Information				PRESENCE	optional	}|
	{ ID	id-DSCH-TDD-Information				CRITICALITY	reject			TYPE	DSCH-TDD-Information			PRESENCE	optional	}|
	{ ID	id-USCH-Information				CRITICALITY	reject			TYPE	USCH-Information			PRESENCE	optional	}|
	{ ID	id-RL-Information-RL-SetupRqstTDD					CRITICALITY	reject			TYPE	RL-Information-RL-SetupRqstTDD					PRESENCE	mandatory 	},
	...
}

RadioLinkSetupRequestTDD-Extensions NBAP-PROTOCOL-EXTENSION ::= {
	{ ID id-HSDSCH-TDD-Information			CRITICALITY reject		EXTENSION HSDSCH-TDD-Information	PRESENCE optional	}|
	{ ID id-HSDSCH-RNTI						CRITICALITY reject		EXTENSION HSDSCH-RNTI			PRESENCE conditional	}|
	-- The IE shall be present if HS-DSCH Information IE is present
	{ ID id-HSPDSCH-RL-ID					CRITICALITY reject		EXTENSION RL-ID					PRESENCE conditional	}|
	-- The IE shall be present if HS-DSCH Information IE is present
	{ ID id-PDSCH-RL-ID						CRITICALITY ignore		EXTENSION RL-ID					PRESENCE optional },
	...
}

UL-CCTrCH-InformationList-RL-SetupRqstTDD ::= SEQUENCE (SIZE(1..maxNrOfCCTrCHs)) OF
	ProtocolIE-Single-Container{{ UL-CCTrCH-InformationItemIE-RL-SetupRqstTDD }}

UL-CCTrCH-InformationItemIE-RL-SetupRqstTDD NBAP-PROTOCOL-IES ::= {
	{ ID	id-UL-CCTrCH-InformationItem-RL-SetupRqstTDD		CRITICALITY		notify			TYPE	UL-CCTrCH-InformationItem-RL-SetupRqstTDD		PRESENCE	mandatory}
}

UL-CCTrCH-InformationItem-RL-SetupRqstTDD ::= SEQUENCE {
	cCTrCH-ID								CCTrCH-ID,
	tFCS									TFCS,
	tFCI-Coding								TFCI-Coding,
	punctureLimit							PunctureLimit,
	uL-DPCH-Information						UL-DPCH-Information-RL-SetupRqstTDD		OPTIONAL, 	-- Applicable to 3.84Mcps TDD only
	iE-Extensions							ProtocolExtensionContainer { { UL-CCTrCH-InformationItem-RL-SetupRqstTDD-ExtIEs} }		OPTIONAL,
	...
}

UL-CCTrCH-InformationItem-RL-SetupRqstTDD-ExtIEs NBAP-PROTOCOL-EXTENSION ::= {
	{ ID id-UL-DPCH-LCR-Information-RL-SetupRqstTDD	CRITICALITY notify		EXTENSION 	UL-DPCH-LCR-Information-RL-SetupRqstTDD		PRESENCE optional	}|	-- Applicable to 1.28Mcps TDD only
	{ ID id-UL-SIRTarget		CRITICALITY reject		EXTENSION		UL-SIR		PRESENCE optional	},
	-- Mandatory for 1.28Mcps TDD, Not Applicable to 3.84Mcps TDD.
	...
}

UL-DPCH-Information-RL-SetupRqstTDD ::= ProtocolIE-Single-Container{{ UL-DPCH-InformationIE-RL-SetupRqstTDD }}

UL-DPCH-InformationIE-RL-SetupRqstTDD NBAP-PROTOCOL-IES ::= {
	{ ID id-UL-DPCH-InformationList-RL-SetupRqstTDD		CRITICALITY notify	TYPE UL-DPCH-InformationItem-RL-SetupRqstTDD		PRESENCE mandatory	}
}

UL-DPCH-InformationItem-RL-SetupRqstTDD ::= SEQUENCE {
	repetitionPeriod						RepetitionPeriod,
	repetitionLength						RepetitionLength,
	tdd-DPCHOffset							TDD-DPCHOffset,
	uL-Timeslot-Information					UL-Timeslot-Information,
	iE-Extensions							ProtocolExtensionContainer { { UL-DPCH-InformationItem-RL-SetupRqstTDD-ExtIEs} }		OPTIONAL,
	...
}

UL-DPCH-InformationItem-RL-SetupRqstTDD-ExtIEs NBAP-PROTOCOL-EXTENSION ::= {
	...
}

UL-DPCH-LCR-Information-RL-SetupRqstTDD ::= SEQUENCE {
	repetitionPeriod						RepetitionPeriod,
	repetitionLength						RepetitionLength,
	tdd-DPCHOffset							TDD-DPCHOffset,
	uL-TimeslotLCR-Information				UL-TimeslotLCR-Information,
	iE-Extensions							ProtocolExtensionContainer { { UL-DPCH-LCR-InformationItem-RL-SetupRqstTDD-ExtIEs} }		OPTIONAL,
	...
}

UL-DPCH-LCR-InformationItem-RL-SetupRqstTDD-ExtIEs NBAP-PROTOCOL-EXTENSION ::= {
	...
}

DL-CCTrCH-InformationList-RL-SetupRqstTDD ::= SEQUENCE (SIZE (1..maxNrOfCCTrCHs)) OF ProtocolIE-Single-Container{{ DL-CCTrCH-InformationItemIE-RL-SetupRqstTDD }}

DL-CCTrCH-InformationItemIE-RL-SetupRqstTDD NBAP-PROTOCOL-IES ::= {
	{ ID	id-DL-CCTrCH-InformationItem-RL-SetupRqstTDD			CRITICALITY		notify			TYPE	DL-CCTrCH-InformationItem-RL-SetupRqstTDD		PRESENCE	mandatory}
}

DL-CCTrCH-InformationItem-RL-SetupRqstTDD ::= SEQUENCE {
	cCTrCH-ID								CCTrCH-ID,
	tFCS									TFCS,
	tFCI-Coding								TFCI-Coding,
	punctureLimit							PunctureLimit,
	tdd-TPC-DownlinkStepSize				TDD-TPC-DownlinkStepSize,
	cCTrCH-TPCList							CCTrCH-TPCList-RL-SetupRqstTDD			OPTIONAL,
	dL-DPCH-Information						DL-DPCH-Information-RL-SetupRqstTDD		OPTIONAL, 	-- Applicable to 3.84Mcps TDD only
	iE-Extensions							ProtocolExtensionContainer { { DL-CCTrCH-InformationItem-RL-SetupRqstTDD-ExtIEs} }		OPTIONAL,
	...
}

DL-CCTrCH-InformationItem-RL-SetupRqstTDD-ExtIEs NBAP-PROTOCOL-EXTENSION ::= {
	{ ID id-DL-DPCH-LCR-Information-RL-SetupRqstTDD	CRITICALITY notify		EXTENSION 	DL-DPCH-LCR-Information-RL-SetupRqstTDD		PRESENCE optional	}|	-- Applicable to 1.28Mcps TDD only
	{ ID id-CCTrCH-Initial-DL-Power-RL-SetupRqstTDD		CRITICALITY ignore		EXTENSION DL-Power		PRESENCE optional	},
	...
}

CCTrCH-TPCList-RL-SetupRqstTDD ::= SEQUENCE (SIZE (1..maxNrOfCCTrCHs)) OF CCTrCH-TPCItem-RL-SetupRqstTDD

CCTrCH-TPCItem-RL-SetupRqstTDD	 ::= SEQUENCE {
	cCTrCH-ID								CCTrCH-ID,
	iE-Extensions							ProtocolExtensionContainer { { CCTrCH-TPCItem-RL-SetupRqstTDD-ExtIEs} }		OPTIONAL,
	...
}

CCTrCH-TPCItem-RL-SetupRqstTDD-ExtIEs NBAP-PROTOCOL-EXTENSION ::= {
	...
}

DL-DPCH-Information-RL-SetupRqstTDD ::= ProtocolIE-Single-Container{{ DL-DPCH-InformationIE-RL-SetupRqstTDD }}

DL-DPCH-InformationIE-RL-SetupRqstTDD NBAP-PROTOCOL-IES ::= {
	{ ID id-DL-DPCH-InformationList-RL-SetupRqstTDD		CRITICALITY notify	TYPE DL-DPCH-InformationItem-RL-SetupRqstTDD		PRESENCE mandatory	}
}

DL-DPCH-InformationItem-RL-SetupRqstTDD	 ::= SEQUENCE {
	repetitionPeriod						RepetitionPeriod,
	repetitionLength						RepetitionLength,
	tdd-DPCHOffset							TDD-DPCHOffset,
	dL-Timeslot-Information				DL-Timeslot-Information,
	iE-Extensions							ProtocolExtensionContainer { { DL-DPCH-InformationItem-RL-SetupRqstTDD-ExtIEs} }		OPTIONAL,
	...
}

DL-DPCH-InformationItem-RL-SetupRqstTDD-ExtIEs NBAP-PROTOCOL-EXTENSION ::= {
	...
}

DL-DPCH-LCR-Information-RL-SetupRqstTDD ::= SEQUENCE {
	repetitionPeriod						RepetitionPeriod,
	repetitionLength						RepetitionLength,
	tdd-DPCHOffset							TDD-DPCHOffset,
	dL-TimeslotLCR-Information				DL-TimeslotLCR-Information,
	tstdIndicator							TSTD-Indicator,
	iE-Extensions							ProtocolExtensionContainer { { DL-DPCH-LCR-InformationItem-RL-SetupRqstTDD-ExtIEs} }		OPTIONAL,
	...
}

DL-DPCH-LCR-InformationItem-RL-SetupRqstTDD-ExtIEs NBAP-PROTOCOL-EXTENSION ::= {
	...
}

RL-Information-RL-SetupRqstTDD ::= SEQUENCE {
	rL-ID									RL-ID,
	c-ID									C-ID,
	frameOffset								FrameOffset,
	specialBurstScheduling					SpecialBurstScheduling,
	initialDL-transmissionPower				DL-Power,
	maximumDL-power							DL-Power,
	minimumDL-power							DL-Power,
	dL-TimeSlotISCPInfo						DL-TimeslotISCPInfo	OPTIONAL, 	-- Applicable to 3.84Mcps TDD only
	iE-Extensions							ProtocolExtensionContainer { { RL-Information-RL-SetupRqstTDD-ExtIEs} }		OPTIONAL,
	...
}

RL-Information-RL-SetupRqstTDD-ExtIEs NBAP-PROTOCOL-EXTENSION ::= {
	{ ID id-TimeslotISCP-LCR-InfoList-RL-SetupRqstTDD	CRITICALITY reject		EXTENSION 	DL-TimeslotISCPInfoLCR		PRESENCE optional	}|
	-- Applicable to 1.28Mcps TDD only
	{ ID id-RL-Specific-DCH-Info	CRITICALITY	ignore		EXTENSION 	RL-Specific-DCH-Info	PRESENCE 	optional	}|
	{ ID id-DelayedActivation CRITICALITY reject EXTENSION DelayedActivation PRESENCE optional }|
	{ ID id-UL-Synchronisation-Parameters-LCR			CRITICALITY	ignore		EXTENSION 	UL-Synchronisation-Parameters-LCR		PRESENCE 	optional	},	-- Mandatory for 1.28Mcps TDD, Not Applicable to 3.84Mcps TDD
	...
}

-- **************************************************************
--
-- RADIO LINK SETUP RESPONSE FDD
--
-- **************************************************************

RadioLinkSetupResponseFDD ::= SEQUENCE {
	protocolIEs				ProtocolIE-Container	{{RadioLinkSetupResponseFDD-IEs}},
	protocolExtensions		ProtocolExtensionContainer	{{RadioLinkSetupResponseFDD-Extensions}}		OPTIONAL,
	...
}

RadioLinkSetupResponseFDD-IEs NBAP-PROTOCOL-IES ::= {
	{ ID	id-CRNC-CommunicationContextID						CRITICALITY	ignore			TYPE	CRNC-CommunicationContextID						PRESENCE	mandatory	}|
	{ ID	id-NodeB-CommunicationContextID						CRITICALITY	ignore			TYPE	NodeB-CommunicationContextID					PRESENCE	mandatory	}|
	{ ID	id-CommunicationControlPortID						CRITICALITY	ignore			TYPE	CommunicationControlPortID						PRESENCE	mandatory	}|
	{ ID	id-RL-InformationResponseList-RL-SetupRspFDD		CRITICALITY	ignore			TYPE	RL-InformationResponseList-RL-SetupRspFDD		PRESENCE	mandatory	}|
	{ ID	id-TFCI2-BearerInformationResponse	CRITICALITY	ignore			TYPE	TFCI2-BearerInformationResponse	PRESENCE	optional	}|
	{ ID	id-CriticalityDiagnostics							CRITICALITY	ignore			TYPE	CriticalityDiagnostics							PRESENCE	optional	},
	...
}

RadioLinkSetupResponseFDD-Extensions NBAP-PROTOCOL-EXTENSION ::= {
	...
}

RL-InformationResponseList-RL-SetupRspFDD ::= SEQUENCE (SIZE (1..maxNrOfRLs)) OF ProtocolIE-Single-Container{{ RL-InformationResponseItemIE-RL-SetupRspFDD }}
	
RL-InformationResponseItemIE-RL-SetupRspFDD NBAP-PROTOCOL-IES ::= {
	{ ID	id-RL-InformationResponseItem-RL-SetupRspFDD			CRITICALITY		ignore		TYPE	RL-InformationResponseItem-RL-SetupRspFDD		PRESENCE	mandatory}
}

RL-InformationResponseItem-RL-SetupRspFDD ::= SEQUENCE {
	rL-ID											RL-ID,
	rL-Set-ID										RL-Set-ID,
	received-total-wide-band-power											Received-total-wide-band-power-Value,
	diversityIndication				DiversityIndication-RL-SetupRspFDD,
	dSCH-InformationResponseList					DSCH-InformationResponseList-RL-SetupRspFDD		OPTIONAL,
	sSDT-SupportIndicator							SSDT-SupportIndicator,
	iE-Extensions									ProtocolExtensionContainer { { RL-InformationResponseItem-RL-SetupRspFDD-ExtIEs} }		OPTIONAL,
	...
}

RL-InformationResponseItem-RL-SetupRspFDD-ExtIEs NBAP-PROTOCOL-EXTENSION ::= {
	{ ID id-DL-PowerBalancing-ActivationIndicator	CRITICALITY ignore		EXTENSION		DL-PowerBalancing-ActivationIndicator		PRESENCE optional}|
	{ ID id-HSDSCH-FDD-Information-Response		CRITICALITY ignore		EXTENSION HSDSCH-FDD-Information-Response		PRESENCE optional	},
	...
}

DiversityIndication-RL-SetupRspFDD ::= CHOICE {
	combining									Combining-RL-SetupRspFDD,
	nonCombiningOrFirstRL						NonCombiningOrFirstRL-RL-SetupRspFDD
}

Combining-RL-SetupRspFDD ::= SEQUENCE {
	rL-ID										RL-ID,
	iE-Extensions								ProtocolExtensionContainer { { Combining-RL-SetupRspFDD-ExtIEs} }		OPTIONAL,
	...
}

Combining-RL-SetupRspFDD-ExtIEs NBAP-PROTOCOL-EXTENSION ::= {
	...
}

NonCombiningOrFirstRL-RL-SetupRspFDD ::= SEQUENCE {
	dCH-InformationResponse						DCH-InformationResponse,
	iE-Extensions									ProtocolExtensionContainer { { NonCombiningOrFirstRLItem-RL-SetupRspFDD-ExtIEs} }		OPTIONAL,
	...
}

NonCombiningOrFirstRLItem-RL-SetupRspFDD-ExtIEs NBAP-PROTOCOL-EXTENSION ::= {
	...
}

DSCH-InformationResponseList-RL-SetupRspFDD ::= ProtocolIE-Single-Container {{ DSCH-InformationResponseListIEs-RL-SetupRspFDD }}

DSCH-InformationResponseListIEs-RL-SetupRspFDD NBAP-PROTOCOL-IES ::= {
	{ ID id-DSCH-InformationResponse   CRITICALITY ignore	TYPE DSCH-InformationResponse		PRESENCE mandatory }
}

-- **************************************************************
--
-- RADIO LINK SETUP RESPONSE TDD
--
-- **************************************************************

RadioLinkSetupResponseTDD ::= SEQUENCE {
	protocolIEs				ProtocolIE-Container	{{RadioLinkSetupResponseTDD-IEs}},
	protocolExtensions		ProtocolExtensionContainer	{{RadioLinkSetupResponseTDD-Extensions}}		OPTIONAL,
	...
}

RadioLinkSetupResponseTDD-IEs NBAP-PROTOCOL-IES ::= {
	{ ID 	id-CRNC-CommunicationContextID						CRITICALITY		ignore			TYPE	CRNC-CommunicationContextID						PRESENCE	mandatory	}|
	{ ID	id-NodeB-CommunicationContextID						CRITICALITY 	ignore			TYPE	NodeB-CommunicationContextID					PRESENCE 	mandatory	}|
	{ ID 	id-CommunicationControlPortID						CRITICALITY 	ignore			TYPE 	CommunicationControlPortID						PRESENCE 	mandatory	}|
	{ ID 	id-RL-InformationResponse-RL-SetupRspTDD			CRITICALITY 	ignore			TYPE	RL-InformationResponse-RL-SetupRspTDD			PRESENCE 	optional	}|	-- Mandatory for 3.84Mcps TDD, Not Applicable to 1.28Mcps TDD
	{ ID 	id-CriticalityDiagnostics							CRITICALITY 	ignore			TYPE	CriticalityDiagnostics							PRESENCE	optional	},
	...
}

RadioLinkSetupResponseTDD-Extensions NBAP-PROTOCOL-EXTENSION ::= {
	{ ID 	id-RL-InformationResponse-LCR-RL-SetupRspTDD			CRITICALITY 	ignore			EXTENSION	RL-InformationResponse-LCR-RL-SetupRspTDD			PRESENCE 	optional	},	-- Mandatory for 1.28Mcps TDD, Not Applicable to 3.84Mcps TDD
	...
}

RL-InformationResponse-RL-SetupRspTDD ::= SEQUENCE {
	rL-ID											RL-ID,
	uL-TimeSlot-ISCP-Info				UL-TimeSlot-ISCP-Info,
	ul-PhysCH-SF-Variation							UL-PhysCH-SF-Variation,
	dCH-InformationResponseList						DCH-InformationResponseList-RL-SetupRspTDD			OPTIONAL,
	dSCH-InformationResponseList					DSCH-InformationResponseList-RL-SetupRspTDD			OPTIONAL,
	uSCH-InformationResponseList					USCH-InformationResponseList-RL-SetupRspTDD			OPTIONAL,
	iE-Extensions									ProtocolExtensionContainer { { RL-InformationResponseList-RL-SetupRspTDD-ExtIEs} }		OPTIONAL,
	...
}

RL-InformationResponseList-RL-SetupRspTDD-ExtIEs NBAP-PROTOCOL-EXTENSION ::= {
	{ ID id-HSDSCH-TDD-Information-Response			CRITICALITY ignore		EXTENSION HSDSCH-TDD-Information-Response		PRESENCE optional	},
	...
}

DCH-InformationResponseList-RL-SetupRspTDD ::= ProtocolIE-Single-Container{{ DCH-InformationResponseListIEs-RL-SetupRspTDD }}

DCH-InformationResponseListIEs-RL-SetupRspTDD NBAP-PROTOCOL-IES ::= {
	{ ID id-DCH-InformationResponse	CRITICALITY 	ignore		TYPE 	DCH-InformationResponse  PRESENCE	mandatory}
 }

DSCH-InformationResponseList-RL-SetupRspTDD ::= ProtocolIE-Single-Container {{ DSCH-InformationResponseListIEs-RL-SetupRspTDD }}

DSCH-InformationResponseListIEs-RL-SetupRspTDD NBAP-PROTOCOL-IES ::= {
	{ ID id-DSCH-InformationResponse   CRITICALITY ignore	TYPE DSCH-InformationResponse		PRESENCE mandatory }
}

USCH-InformationResponseList-RL-SetupRspTDD ::= ProtocolIE-Single-Container {{ USCH-InformationResponseListIEs-RL-SetupRspTDD }}

USCH-InformationResponseListIEs-RL-SetupRspTDD NBAP-PROTOCOL-IES ::= {
	{ ID id-USCH-InformationResponse   CRITICALITY ignore	TYPE USCH-InformationResponse		PRESENCE mandatory }
}

RL-InformationResponse-LCR-RL-SetupRspTDD ::= SEQUENCE {
	rL-ID											RL-ID,
	uL-TimeSlot-ISCP-LCR-Info						UL-TimeSlot-ISCP-LCR-Info,
	ul-PhysCH-SF-Variation							UL-PhysCH-SF-Variation,
	dCH-InformationResponseList						DCH-InformationResponseList-RL-SetupRspTDD			OPTIONAL,
	dSCH-InformationResponseList					DSCH-InformationResponseList-RL-SetupRspTDD			OPTIONAL,
	uSCH-InformationResponseList					USCH-InformationResponseList-RL-SetupRspTDD			OPTIONAL,
	iE-Extensions									ProtocolExtensionContainer { { RL-InformationResponseList-LCR-RL-SetupRspTDD-ExtIEs} }		OPTIONAL,
	...
}

RL-InformationResponseList-LCR-RL-SetupRspTDD-ExtIEs NBAP-PROTOCOL-EXTENSION ::= {
	{ ID id-HSDSCH-TDD-Information-Response-LCR			CRITICALITY ignore		EXTENSION HSDSCH-TDD-Information-Response		PRESENCE optional	},
	...
}

-- **************************************************************
--
-- RADIO LINK SETUP FAILURE FDD
--
-- **************************************************************

RadioLinkSetupFailureFDD ::= SEQUENCE {
	protocolIEs				ProtocolIE-Container	{{RadioLinkSetupFailureFDD-IEs}},
	protocolExtensions		ProtocolExtensionContainer	{{RadioLinkSetupFailureFDD-Extensions}}		OPTIONAL,
	...
}

RadioLinkSetupFailureFDD-IEs NBAP-PROTOCOL-IES ::= {
	{ ID	id-CRNC-CommunicationContextID									CRITICALITY		ignore			TYPE	CRNC-CommunicationContextID									PRESENCE 	mandatory	}|
	{ ID	id-NodeB-CommunicationContextID									CRITICALITY		ignore			TYPE	NodeB-CommunicationContextID								PRESENCE	conditional	}|
	-- This IE shall be present if at least one of the radio links has been successfully set up
	{ ID	id-CommunicationControlPortID									CRITICALITY		ignore			TYPE	CommunicationControlPortID									PRESENCE	optional 	}|
	{ ID    id-CauseLevel-RL-SetupFailureFDD								CRITICALITY		ignore			TYPE	CauseLevel-RL-SetupFailureFDD		PRESENCE   mandatory	}|
	{ ID	id-CriticalityDiagnostics										CRITICALITY		ignore			TYPE	CriticalityDiagnostics										PRESENCE	optional	},
	...
}

RadioLinkSetupFailureFDD-Extensions NBAP-PROTOCOL-EXTENSION ::= {
	...
}

CauseLevel-RL-SetupFailureFDD ::= CHOICE {
	generalCause		GeneralCauseList-RL-SetupFailureFDD,
	rLSpecificCause		RLSpecificCauseList-RL-SetupFailureFDD,
	...
}

GeneralCauseList-RL-SetupFailureFDD ::= SEQUENCE {
	cause										Cause,
	iE-Extensions								ProtocolExtensionContainer { { GeneralCauseItem-RL-SetupFailureFDD-ExtIEs} }		OPTIONAL,
	...
}

GeneralCauseItem-RL-SetupFailureFDD-ExtIEs NBAP-PROTOCOL-EXTENSION ::= {
	...
}

RLSpecificCauseList-RL-SetupFailureFDD ::= SEQUENCE {
	unsuccessful-RL-InformationRespList-RL-SetupFailureFDD		Unsuccessful-RL-InformationRespList-RL-SetupFailureFDD,
	successful-RL-InformationRespList-RL-SetupFailureFDD		Successful-RL-InformationRespList-RL-SetupFailureFDD	OPTIONAL,
	iE-Extensions								ProtocolExtensionContainer { { RLSpecificCauseItem-RL-SetupFailureFDD-ExtIEs} }		OPTIONAL,
	...
}

RLSpecificCauseItem-RL-SetupFailureFDD-ExtIEs NBAP-PROTOCOL-EXTENSION ::= {
	...
}

Unsuccessful-RL-InformationRespList-RL-SetupFailureFDD ::= SEQUENCE (SIZE (1..maxNrOfRLs))	OF ProtocolIE-Single-Container {{ Unsuccessful-RL-InformationRespItemIE-RL-SetupFailureFDD }}

Unsuccessful-RL-InformationRespItemIE-RL-SetupFailureFDD NBAP-PROTOCOL-IES ::= {
	{ ID	id-Unsuccessful-RL-InformationRespItem-RL-SetupFailureFDD		CRITICALITY		ignore		TYPE	Unsuccessful-RL-InformationRespItem-RL-SetupFailureFDD		PRESENCE	mandatory}
}

Unsuccessful-RL-InformationRespItem-RL-SetupFailureFDD ::= SEQUENCE {
	rL-ID										RL-ID,
	cause										Cause,
	iE-Extensions								ProtocolExtensionContainer { { Unsuccessful-RL-InformationRespItem-RL-SetupFailureFDD-ExtIEs} }		OPTIONAL,
	...
}

Unsuccessful-RL-InformationRespItem-RL-SetupFailureFDD-ExtIEs NBAP-PROTOCOL-EXTENSION ::= {
	...
}

Successful-RL-InformationRespList-RL-SetupFailureFDD ::= SEQUENCE (SIZE (1.. maxNrOfRLs)) OF ProtocolIE-Single-Container	{{ Successful-RL-InformationRespItemIE-RL-SetupFailureFDD }}

Successful-RL-InformationRespItemIE-RL-SetupFailureFDD NBAP-PROTOCOL-IES ::= {
	{ ID	id-Successful-RL-InformationRespItem-RL-SetupFailureFDD			CRITICALITY		ignore 		TYPE	Successful-RL-InformationRespItem-RL-SetupFailureFDD		PRESENCE	mandatory}
}

Successful-RL-InformationRespItem-RL-SetupFailureFDD ::= SEQUENCE {
	rL-ID										RL-ID,
	rL-Set-ID									RL-Set-ID,
	received-total-wide-band-power										Received-total-wide-band-power-Value,
	diversityIndication							DiversityIndication-RL-SetupFailureFDD,
	dSCH-InformationResponseList				DSCH-InformationRespList-RL-SetupFailureFDD		OPTIONAL,
	tFCI2-BearerInformationResponse				TFCI2-BearerInformationResponse 	OPTIONAL,
	-- There shall be only one TFCI2 bearer per Node B Communication Context.
	sSDT-SupportIndicator						SSDT-SupportIndicator,
	iE-Extensions								ProtocolExtensionContainer { { Successful-RL-InformationRespItem-RL-SetupFailureFDD-ExtIEs} }		OPTIONAL,
	...
}

Successful-RL-InformationRespItem-RL-SetupFailureFDD-ExtIEs NBAP-PROTOCOL-EXTENSION ::= {
	{ ID id-DL-PowerBalancing-ActivationIndicator	CRITICALITY ignore		EXTENSION		DL-PowerBalancing-ActivationIndicator		PRESENCE optional}|
	{ ID id-HSDSCH-FDD-Information-Response			CRITICALITY ignore 		EXTENSION HSDSCH-FDD-Information-Response		PRESENCE optional	},
	...
}

DiversityIndication-RL-SetupFailureFDD ::= CHOICE {
 	combining									Combining-RL-SetupFailureFDD,
 	nonCombiningOrFirstRL					NonCombiningOrFirstRL-RL-SetupFailureFDD
}

Combining-RL-SetupFailureFDD ::= SEQUENCE {
 	rL-ID										RL-ID,
	iE-Extensions								ProtocolExtensionContainer { { CombiningItem-RL-SetupFailureFDD-ExtIEs} }		OPTIONAL,
	...
 }

CombiningItem-RL-SetupFailureFDD-ExtIEs NBAP-PROTOCOL-EXTENSION ::= {
	...
}

NonCombiningOrFirstRL-RL-SetupFailureFDD ::= SEQUENCE {
 	dCH-InformationResponse						DCH-InformationResponse,
	iE-Extensions									ProtocolExtensionContainer { { NonCombiningOrFirstRLItem-RL-SetupFailureFDD-ExtIEs} }		OPTIONAL,
	...
}

NonCombiningOrFirstRLItem-RL-SetupFailureFDD-ExtIEs NBAP-PROTOCOL-EXTENSION ::= {
	...
}

DSCH-InformationRespList-RL-SetupFailureFDD ::= ProtocolIE-Single-Container {{ DSCH-InformationRespListIEs-RL-SetupFailureFDD }}

DSCH-InformationRespListIEs-RL-SetupFailureFDD NBAP-PROTOCOL-IES ::= {
	{ ID id-DSCH-InformationResponse   CRITICALITY ignore	TYPE DSCH-InformationResponse		PRESENCE mandatory }
}

-- **************************************************************
--
-- RADIO LINK SETUP FAILURE TDD
--
-- **************************************************************

RadioLinkSetupFailureTDD ::= SEQUENCE {
	protocolIEs				ProtocolIE-Container	{{RadioLinkSetupFailureTDD-IEs}},
	protocolExtensions		ProtocolExtensionContainer	{{RadioLinkSetupFailureTDD-Extensions}}			OPTIONAL,
	...
}

RadioLinkSetupFailureTDD-IEs NBAP-PROTOCOL-IES ::= {
	{ ID	id-CRNC-CommunicationContextID								CRITICALITY	ignore		TYPE	CRNC-CommunicationContextID								PRESENCE	mandatory	}|
	{ ID    id-CauseLevel-RL-SetupFailureTDD								CRITICALITY		ignore			TYPE	CauseLevel-RL-SetupFailureTDD		PRESENCE   mandatory	}|
	{ ID	id-CriticalityDiagnostics									CRITICALITY	ignore		TYPE	CriticalityDiagnostics									PRESENCE	optional	},
	...
}

RadioLinkSetupFailureTDD-Extensions NBAP-PROTOCOL-EXTENSION ::= {
	...
}

CauseLevel-RL-SetupFailureTDD ::= CHOICE {
	generalCause		GeneralCauseList-RL-SetupFailureTDD,
	rLSpecificCause		RLSpecificCauseList-RL-SetupFailureTDD,
	...
}

GeneralCauseList-RL-SetupFailureTDD ::= SEQUENCE {
	cause						Cause,
	iE-Extensions				ProtocolExtensionContainer { { GeneralCauseItem-RL-SetupFailureTDD-ExtIEs} }		OPTIONAL,
	...
}

GeneralCauseItem-RL-SetupFailureTDD-ExtIEs NBAP-PROTOCOL-EXTENSION ::= {
	...
}

RLSpecificCauseList-RL-SetupFailureTDD ::= SEQUENCE {
	unsuccessful-RL-InformationRespItem-RL-SetupFailureTDD	Unsuccessful-RL-InformationRespItem-RL-SetupFailureTDD,
	iE-Extensions											ProtocolExtensionContainer { { RLSpecificCauseItem-RL-SetupFailureTDD-ExtIEs} }		OPTIONAL,
	...
}

RLSpecificCauseItem-RL-SetupFailureTDD-ExtIEs NBAP-PROTOCOL-EXTENSION ::= {
	...
}

Unsuccessful-RL-InformationRespItem-RL-SetupFailureTDD ::= ProtocolIE-Single-Container { {Unsuccessful-RL-InformationRespItemIE-RL-SetupFailureTDD} }

Unsuccessful-RL-InformationRespItemIE-RL-SetupFailureTDD NBAP-PROTOCOL-IES ::= {
	{ ID	id-Unsuccessful-RL-InformationResp-RL-SetupFailureTDD		CRITICALITY	ignore 		TYPE 	Unsuccessful-RL-InformationResp-RL-SetupFailureTDD		PRESENCE	mandatory	}
}

Unsuccessful-RL-InformationResp-RL-SetupFailureTDD ::= SEQUENCE {
	rL-ID										RL-ID,
	cause										Cause,
	iE-Extensions								ProtocolExtensionContainer { { Unsuccessful-RL-InformationResp-RL-SetupFailureTDD-ExtIEs} }		OPTIONAL,
	...
}

Unsuccessful-RL-InformationResp-RL-SetupFailureTDD-ExtIEs NBAP-PROTOCOL-EXTENSION ::= {
	...
}

-- **************************************************************
--
-- RADIO LINK ADDITION REQUEST FDD
--
-- **************************************************************

RadioLinkAdditionRequestFDD ::= SEQUENCE {
	protocolIEs				ProtocolIE-Container	{{RadioLinkAdditionRequestFDD-IEs}},
	protocolExtensions		ProtocolExtensionContainer	{{RadioLinkAdditionRequestFDD-Extensions}}			OPTIONAL,
	...
}

RadioLinkAdditionRequestFDD-IEs NBAP-PROTOCOL-IES ::= {
	{ ID	id-NodeB-CommunicationContextID					CRITICALITY	reject			TYPE	NodeB-CommunicationContextID					PRESENCE	mandatory	} |
	{ ID id-Compressed-Mode-Deactivation-Flag		CRITICALITY reject				TYPE Compressed-Mode-Deactivation-Flag	 PRESENCE optional }|
	{ ID	id-RL-InformationList-RL-AdditionRqstFDD			CRITICALITY	notify			TYPE	RL-InformationList-RL-AdditionRqstFDD			PRESENCE	mandatory	},
	...
}

RadioLinkAdditionRequestFDD-Extensions NBAP-PROTOCOL-EXTENSION ::= {
	...
}

RL-InformationList-RL-AdditionRqstFDD	::= SEQUENCE (SIZE (1..maxNrOfRLs-1)) OF ProtocolIE-Single-Container {{ RL-InformationItemIE-RL-AdditionRqstFDD}}

RL-InformationItemIE-RL-AdditionRqstFDD NBAP-PROTOCOL-IES ::= {
	{ ID	id-RL-InformationItem-RL-AdditionRqstFDD			CRITICALITY		notify			TYPE	RL-InformationItem-RL-AdditionRqstFDD			PRESENCE	mandatory}
}

RL-InformationItem-RL-AdditionRqstFDD ::= SEQUENCE {
	rL-ID										RL-ID,
	c-ID										C-ID,
	frameOffset									FrameOffset,
	chipOffset									ChipOffset,
	diversityControlField						DiversityControlField,
	dl-CodeInformation						FDD-DL-CodeInformation,
	initialDL-TransmissionPower					DL-Power						OPTIONAL,
 	maximumDL-Power								DL-Power						OPTIONAL,
 	minimumDL-Power								DL-Power						OPTIONAL,
 	sSDT-CellIdentity							SSDT-Cell-Identity				OPTIONAL,
	transmitDiversityIndicator					TransmitDiversityIndicator		OPTIONAL,
	iE-Extensions								ProtocolExtensionContainer { { RL-InformationItem-RL-AdditionRqstFDD-ExtIEs} }		OPTIONAL,
	...
}

RL-InformationItem-RL-AdditionRqstFDD-ExtIEs NBAP-PROTOCOL-EXTENSION ::= {
	{ ID id-DLReferencePower	CRITICALITY ignore		EXTENSION	DL-Power		PRESENCE optional}|
	{ ID id-RL-Specific-DCH-Info		CRITICALITY	ignore		EXTENSION 	RL-Specific-DCH-Info	PRESENCE 	optional	}|
	{ ID id-DelayedActivation CRITICALITY reject EXTENSION DelayedActivation PRESENCE optional }|
	{ ID id-Qth-Parameter	CRITICALITY ignore		EXTENSION	Qth-Parameter 		PRESENCE optional },
	...
}

-- **************************************************************
--
-- RADIO LINK ADDITION REQUEST TDD
--
-- **************************************************************

RadioLinkAdditionRequestTDD ::= SEQUENCE {
	protocolIEs				ProtocolIE-Container	{{RadioLinkAdditionRequestTDD-IEs}},
	protocolExtensions		ProtocolExtensionContainer	{{RadioLinkAdditionRequestTDD-Extensions}}		OPTIONAL,
	...
}

RadioLinkAdditionRequestTDD-IEs NBAP-PROTOCOL-IES ::= {
	{ ID	id-NodeB-CommunicationContextID							CRITICALITY		reject			TYPE	NodeB-CommunicationContextID						PRESENCE	mandatory	}|
	{ ID	id-UL-CCTrCH-InformationList-RL-AdditionRqstTDD			CRITICALITY		reject			TYPE	UL-CCTrCH-InformationList-RL-AdditionRqstTDD			PRESENCE	optional	}|
	{ ID	id-DL-CCTrCH-InformationList-RL-AdditionRqstTDD			CRITICALITY		reject			TYPE	DL-CCTrCH-InformationList-RL-AdditionRqstTDD			PRESENCE	optional	}|
	{ ID	id-RL-Information-RL-AdditionRqstTDD					CRITICALITY		reject			TYPE	RL-Information-RL-AdditionRqstTDD					PRESENCE	mandatory	},
	...
}

RadioLinkAdditionRequestTDD-Extensions NBAP-PROTOCOL-EXTENSION ::= {
	...
}

UL-CCTrCH-InformationList-RL-AdditionRqstTDD ::= SEQUENCE (SIZE (1..maxNrOfCCTrCHs)) OF UL-CCTrCH-InformationItem-RL-AdditionRqstTDD

UL-CCTrCH-InformationItem-RL-AdditionRqstTDD ::= SEQUENCE {
	cCTrCH-ID									CCTrCH-ID,
	uL-DPCH-Information							UL-DPCH-InformationList-RL-AdditionRqstTDD		OPTIONAL, -- Applicable to 3.84cps TDD only
	iE-Extensions								ProtocolExtensionContainer { { UL-CCTrCH-InformationItem-RL-AdditionRqstTDD-ExtIEs} }		OPTIONAL,
	...
}

UL-CCTrCH-InformationItem-RL-AdditionRqstTDD-ExtIEs NBAP-PROTOCOL-EXTENSION ::= {
	{ ID	id-UL-DPCH-InformationItem-LCR-RL-AdditionRqstTDD			CRITICALITY		notify			EXTENSION	UL-DPCH-InformationItem-LCR-RL-AdditionRqstTDD			PRESENCE	optional },	-- Applicable to 1.28cps TDD only
	...
}

UL-DPCH-InformationList-RL-AdditionRqstTDD ::= ProtocolIE-Single-Container {{ UL-DPCH-InformationItemIE-RL-AdditionRqstTDD }}

UL-DPCH-InformationItemIE-RL-AdditionRqstTDD NBAP-PROTOCOL-IES ::= {
	{ ID	id-UL-DPCH-InformationItem-RL-AdditionRqstTDD			CRITICALITY		notify			TYPE	UL-DPCH-InformationItem-RL-AdditionRqstTDD			PRESENCE	optional}	-- For 3.84Mcps TDD only
}

UL-DPCH-InformationItem-RL-AdditionRqstTDD ::= SEQUENCE {	
	repetitionPeriod						RepetitionPeriod,
	repetitionLength						RepetitionLength,
	tdd-DPCHOffset							TDD-DPCHOffset,
	uL-Timeslot-Information				UL-Timeslot-Information,
	iE-Extensions								ProtocolExtensionContainer { { UL-DPCH-InformationItem-RL-AdditionRqstTDD-ExtIEs} }		OPTIONAL,
	...
}

UL-DPCH-InformationItem-RL-AdditionRqstTDD-ExtIEs  NBAP-PROTOCOL-EXTENSION ::= {
	...
}

DL-CCTrCH-InformationList-RL-AdditionRqstTDD ::= SEQUENCE (SIZE (1..maxNrOfCCTrCHs)) OF DL-CCTrCH-InformationItem-RL-AdditionRqstTDD

DL-CCTrCH-InformationItem-RL-AdditionRqstTDD ::= SEQUENCE {
	cCTrCH-ID									CCTrCH-ID,
	dL-DPCH-Information							DL-DPCH-InformationList-RL-AdditionRqstTDD		OPTIONAL,
	iE-Extensions								ProtocolExtensionContainer { { DL-CCTrCH-InformationItem-RL-AdditionRqstTDD-ExtIEs} }		OPTIONAL,
	...
}

DL-CCTrCH-InformationItem-RL-AdditionRqstTDD-ExtIEs  NBAP-PROTOCOL-EXTENSION ::= {
	{ ID	id-DL-DPCH-InformationItem-LCR-RL-AdditionRqstTDD			CRITICALITY		notify			EXTENSION	DL-DPCH-InformationItem-LCR-RL-AdditionRqstTDD			PRESENCE	optional }|	-- Applicable to 1.28Mcps TDD only
	{ ID id-CCTrCH-Initial-DL-Power-RL-AdditionRqstTDD		CRITICALITY ignore		EXTENSION DL-Power		PRESENCE optional	},
	...
}

DL-DPCH-InformationList-RL-AdditionRqstTDD ::= ProtocolIE-Single-Container {{ DL-DPCH-InformationItemIE-RL-AdditionRqstTDD }}

DL-DPCH-InformationItemIE-RL-AdditionRqstTDD NBAP-PROTOCOL-IES ::= {
	{ ID	id-DL-DPCH-InformationItem-RL-AdditionRqstTDD			CRITICALITY		notify			TYPE	DL-DPCH-InformationItem-RL-AdditionRqstTDD			PRESENCE 	mandatory}	-- Applicable to 3.84Mcps TDD only
}

DL-DPCH-InformationItem-RL-AdditionRqstTDD ::= SEQUENCE {
	repetitionPeriod						RepetitionPeriod,
	repetitionLength						RepetitionLength,
	tdd-DPCHOffset							TDD-DPCHOffset,
	dL-Timeslot-Information				DL-Timeslot-Information,
	iE-Extensions								ProtocolExtensionContainer { { DL-DPCH-InformationItem-RL-AdditionRqstTDD-ExtIEs} }			OPTIONAL,
	...
}

DL-DPCH-InformationItem-RL-AdditionRqstTDD-ExtIEs  NBAP-PROTOCOL-EXTENSION ::= {
	...
}

RL-Information-RL-AdditionRqstTDD ::= SEQUENCE {
 	rL-ID										RL-ID,
 	c-ID										C-ID,
 	frameOffset									FrameOffset,
 	diversityControlField						DiversityControlField,
	initial-DL-Transmission-Power				DL-Power			OPTIONAL,
 	maximumDL-Power								DL-Power			OPTIONAL,
 	minimumDL-Power								DL-Power			OPTIONAL,
	dL-TimeSlotISCPInfo							DL-TimeslotISCPInfo	OPTIONAL, 	-- Applicable to 3.84Mcps TDD only
	iE-Extensions								ProtocolExtensionContainer { { RL-information-RL-AdditionRqstTDD-ExtIEs} }			OPTIONAL,
	...
 }

RL-information-RL-AdditionRqstTDD-ExtIEs  NBAP-PROTOCOL-EXTENSION ::= {
	{ ID id-TimeslotISCP-InformationList-LCR-RL-AdditionRqstTDD			CRITICALITY		reject			EXTENSION	DL-TimeslotISCPInfoLCR			PRESENCE	optional }|	-- Applicable to 1.28Mcps TDD only
	{ ID id-RL-Specific-DCH-Info		CRITICALITY	ignore		EXTENSION 	RL-Specific-DCH-Info	PRESENCE 	optional	}|
	{ ID id-DelayedActivation CRITICALITY reject EXTENSION DelayedActivation PRESENCE optional }|
	{ ID id-UL-Synchronisation-Parameters-LCR			CRITICALITY	ignore		EXTENSION 	UL-Synchronisation-Parameters-LCR		PRESENCE 	optional	},	-- Mandatory for 1.28Mcps TDD, Not Applicable to 3.84Mcps TDD
	...
}

UL-DPCH-InformationItem-LCR-RL-AdditionRqstTDD ::= SEQUENCE {
	repetitionPeriod						RepetitionPeriod,
	repetitionLength						RepetitionLength,
	tdd-DPCHOffset							TDD-DPCHOffset,
	uL-TimeslotLCR-Information				UL-TimeslotLCR-Information,
	iE-Extensions							ProtocolExtensionContainer { { UL-DPCH-InformationItem-LCR-RL-AdditionRqstTDD-ExtIEs} }		OPTIONAL,
	...
}

UL-DPCH-InformationItem-LCR-RL-AdditionRqstTDD-ExtIEs NBAP-PROTOCOL-EXTENSION ::= {
	...
}

DL-DPCH-InformationItem-LCR-RL-AdditionRqstTDD ::= SEQUENCE {
	repetitionPeriod						RepetitionPeriod,
	repetitionLength						RepetitionLength,
	tdd-DPCHOffset							TDD-DPCHOffset,
	dL-TimeslotLCR-Information				DL-TimeslotLCR-Information,
	iE-Extensions							ProtocolExtensionContainer { { DL-DPCH-InformationItem-LCR-RL-AdditionRqstTDD-ExtIEs} }		OPTIONAL,
	...
}

DL-DPCH-InformationItem-LCR-RL-AdditionRqstTDD-ExtIEs NBAP-PROTOCOL-EXTENSION ::= {
	...
}

-- **************************************************************
--
-- RADIO LINK ADDITION RESPONSE FDD
--
-- **************************************************************

RadioLinkAdditionResponseFDD ::= SEQUENCE {
	protocolIEs				ProtocolIE-Container	{{RadioLinkAdditionResponseFDD-IEs}},
	protocolExtensions		ProtocolExtensionContainer	{{RadioLinkAdditionResponseFDD-Extensions}}			OPTIONAL,
	...
}

RadioLinkAdditionResponseFDD-IEs NBAP-PROTOCOL-IES ::= {
	{ ID	id-CRNC-CommunicationContextID							CRITICALITY		ignore				TYPE	CRNC-CommunicationContextID						PRESENCE	mandatory	}|
	{ ID	id-RL-InformationResponseList-RL-AdditionRspFDD			CRITICALITY		ignore				TYPE	RL-InformationResponseList-RL-AdditionRspFDD	PRESENCE	mandatory	}|
	{ ID	id-CriticalityDiagnostics								CRITICALITY		ignore				TYPE	CriticalityDiagnostics							PRESENCE	optional	},
	...
}

RadioLinkAdditionResponseFDD-Extensions NBAP-PROTOCOL-EXTENSION ::= {
	...
}

RL-InformationResponseList-RL-AdditionRspFDD ::= SEQUENCE (SIZE (1..maxNrOfRLs-1)) OF ProtocolIE-Single-Container {{ RL-InformationResponseItemIE-RL-AdditionRspFDD }}

RL-InformationResponseItemIE-RL-AdditionRspFDD NBAP-PROTOCOL-IES ::= {
	{ ID	id-RL-InformationResponseItem-RL-AdditionRspFDD			CRITICALITY		ignore			TYPE	RL-InformationResponseItem-RL-AdditionRspFDD		PRESENCE	mandatory}
}

RL-InformationResponseItem-RL-AdditionRspFDD ::= SEQUENCE {
	rL-ID											RL-ID,
	rL-Set-ID										RL-Set-ID,
	received-total-wide-band-power											Received-total-wide-band-power-Value,
	diversityIndication								DiversityIndication-RL-AdditionRspFDD,
	sSDT-SupportIndicator							SSDT-SupportIndicator,
	iE-Extensions									ProtocolExtensionContainer { { RL-InformationResponseItem-RL-AdditionRspFDD-ExtIEs} }		OPTIONAL,
	...
}

RL-InformationResponseItem-RL-AdditionRspFDD-ExtIEs  NBAP-PROTOCOL-EXTENSION ::= {
	{ ID id-DL-PowerBalancing-ActivationIndicator	CRITICALITY ignore		EXTENSION		DL-PowerBalancing-ActivationIndicator		PRESENCE optional},
	...
}

DiversityIndication-RL-AdditionRspFDD ::= CHOICE {
	combining										Combining-RL-AdditionRspFDD,
	non-combining									Non-Combining-RL-AdditionRspFDD
}

Combining-RL-AdditionRspFDD ::= SEQUENCE {
 	rL-ID											RL-ID,
	iE-Extensions									ProtocolExtensionContainer { { CombiningItem-RL-AdditionRspFDD-ExtIEs} }		OPTIONAL,
	...
}

CombiningItem-RL-AdditionRspFDD-ExtIEs  NBAP-PROTOCOL-EXTENSION ::= {
	...
}

Non-Combining-RL-AdditionRspFDD ::= SEQUENCE {
	dCH-InformationResponse						DCH-InformationResponse,
	iE-Extensions									ProtocolExtensionContainer { { Non-CombiningItem-RL-AdditionRspFDD-ExtIEs} }		OPTIONAL,
	...
}

Non-CombiningItem-RL-AdditionRspFDD-ExtIEs  NBAP-PROTOCOL-EXTENSION ::= {
	...
}

-- **************************************************************
--
-- RADIO LINK ADDITION RESPONSE TDD
--
-- **************************************************************

RadioLinkAdditionResponseTDD ::= SEQUENCE {
	protocolIEs				ProtocolIE-Container	{{RadioLinkAdditionResponseTDD-IEs}},
	protocolExtensions		ProtocolExtensionContainer	{{RadioLinkAdditionResponseTDD-Extensions}}		OPTIONAL,
	...
}

RadioLinkAdditionResponseTDD-IEs NBAP-PROTOCOL-IES ::= {
	{ ID	id-CRNC-CommunicationContextID						CRITICALITY	ignore			TYPE	CRNC-CommunicationContextID						PRESENCE 	mandatory	}|
	{ ID	id-RL-InformationResponse-RL-AdditionRspTDD			CRITICALITY	ignore			TYPE	RL-InformationResponse-RL-AdditionRspTDD		PRESENCE 	optional	}|		-- Mandatory for 3.84Mcps TDD, Not Applicable to 1.28Mcps TDD
	{ ID	id-CriticalityDiagnostics							CRITICALITY	ignore			TYPE	CriticalityDiagnostics							PRESENCE	optional	},
	...
}

RadioLinkAdditionResponseTDD-Extensions NBAP-PROTOCOL-EXTENSION ::= {
	{ ID id-RL-InformationResponse-LCR-RL-AdditionRspTDD		CRITICALITY ignore			EXTENSION	RL-InformationResponse-LCR-RL-AdditionRspTDD 	PRESENCE optional },	-- Mandatory for 1.28Mcps TDD, Not Applicable to 3.84Mcps TDD
	...
}

RL-InformationResponse-RL-AdditionRspTDD ::= SEQUENCE {
	rL-ID										RL-ID,
	uL-TimeSlot-ISCP-Info						UL-TimeSlot-ISCP-Info,
	ul-PhysCH-SF-Variation						UL-PhysCH-SF-Variation,
	dCH-Information								DCH-Information-RL-AdditionRspTDD				OPTIONAL,
	dSCH-InformationResponseList				DSCH-InformationResponseList-RL-AdditionRspTDD		OPTIONAL,
	uSCH-InformationResponseList				USCH-InformationResponseList-RL-AdditionRspTDD		OPTIONAL,
	iE-Extensions								ProtocolExtensionContainer { { RL-InformationResponse-RL-AdditionRspTDD-ExtIEs} }		OPTIONAL,
	...
}

RL-InformationResponse-RL-AdditionRspTDD-ExtIEs  NBAP-PROTOCOL-EXTENSION ::= {
	...
}

DCH-Information-RL-AdditionRspTDD ::= SEQUENCE {
	diversityIndication					DiversityIndication-RL-AdditionRspTDD,
	iE-Extensions					ProtocolExtensionContainer { { DCH-Information-RL-AdditionRspTDD-ExtIEs} } OPTIONAL,
	...
}

DCH-Information-RL-AdditionRspTDD-ExtIEs NBAP-PROTOCOL-EXTENSION ::= {
	...
}

DiversityIndication-RL-AdditionRspTDD ::= CHOICE {
	combining									Combining-RL-AdditionRspTDD,
	non-Combining								Non-Combining-RL-AdditionRspTDD
}

Combining-RL-AdditionRspTDD ::= SEQUENCE {
	rL-ID										RL-ID,
	iE-Extensions								ProtocolExtensionContainer { { CombiningItem-RL-AdditionRspTDD-ExtIEs} }		OPTIONAL,
	...
}

CombiningItem-RL-AdditionRspTDD-ExtIEs  NBAP-PROTOCOL-EXTENSION ::= {
	...
}

Non-Combining-RL-AdditionRspTDD ::= SEQUENCE {
	dCH-InformationResponse					DCH-InformationResponse,
	iE-Extensions								ProtocolExtensionContainer { { Non-CombiningItem-RL-AdditionRspTDD-ExtIEs} }			OPTIONAL,
	...
}

Non-CombiningItem-RL-AdditionRspTDD-ExtIEs  NBAP-PROTOCOL-EXTENSION ::= {
	...
}

DSCH-InformationResponseList-RL-AdditionRspTDD ::= ProtocolIE-Single-Container {{ DSCH-InformationResponseListIEs-RL-AdditionRspTDD }}

DSCH-InformationResponseListIEs-RL-AdditionRspTDD NBAP-PROTOCOL-IES ::= {
	{ ID id-DSCH-InformationResponse   CRITICALITY ignore	TYPE DSCH-InformationResponse		PRESENCE mandatory }
}

USCH-InformationResponseList-RL-AdditionRspTDD ::= ProtocolIE-Single-Container {{ USCH-InformationResponseListIEs-RL-AdditionRspTDD }}

USCH-InformationResponseListIEs-RL-AdditionRspTDD NBAP-PROTOCOL-IES ::= {
	{ ID id-USCH-InformationResponse   CRITICALITY ignore	TYPE USCH-InformationResponse		PRESENCE mandatory }
}

RL-InformationResponse-LCR-RL-AdditionRspTDD ::= SEQUENCE {
	rL-ID										RL-ID,
	uL-TimeSlot-ISCP-InfoLCR					UL-TimeSlot-ISCP-LCR-Info,
	ul-PhysCH-SF-Variation						UL-PhysCH-SF-Variation,
	dCH-Information								DCH-Information-RL-AdditionRspTDD				OPTIONAL,
	dSCH-InformationResponseList				DSCH-InformationResponseList-RL-AdditionRspTDD		OPTIONAL,
	uSCH-InformationResponseList				USCH-InformationResponseList-RL-AdditionRspTDD		OPTIONAL,
	iE-Extensions								ProtocolExtensionContainer { { RL-InformationResponse-LCR-RL-AdditionRspTDD-ExtIEs} }		OPTIONAL,
	...
}

RL-InformationResponse-LCR-RL-AdditionRspTDD-ExtIEs  NBAP-PROTOCOL-EXTENSION ::= {
	...
}

-- **************************************************************
--
-- RADIO LINK ADDITION FAILURE FDD
--
-- **************************************************************

RadioLinkAdditionFailureFDD ::= SEQUENCE {
	protocolIEs				ProtocolIE-Container	{{RadioLinkAdditionFailureFDD-IEs}},
	protocolExtensions		ProtocolExtensionContainer	{{RadioLinkAdditionFailureFDD-Extensions}}		OPTIONAL,
	...
}

RadioLinkAdditionFailureFDD-IEs NBAP-PROTOCOL-IES ::= {
	{ ID	id-CRNC-CommunicationContextID			CRITICALITY		ignore		TYPE	CRNC-CommunicationContextID				PRESENCE mandatory	}|
	{ ID    id-CauseLevel-RL-AdditionFailureFDD		CRITICALITY		ignore		TYPE	CauseLevel-RL-AdditionFailureFDD		PRESENCE	mandatory 	}|
	{ ID	id-CriticalityDiagnostics				CRITICALITY		ignore		TYPE	CriticalityDiagnostics					PRESENCE optional		},
	...
}

RadioLinkAdditionFailureFDD-Extensions NBAP-PROTOCOL-EXTENSION ::= {
	...
}

CauseLevel-RL-AdditionFailureFDD ::= CHOICE {
	generalCause		GeneralCauseList-RL-AdditionFailureFDD,
	rLSpecificCause		RLSpecificCauseList-RL-AdditionFailureFDD,
	...
}

GeneralCauseList-RL-AdditionFailureFDD ::= SEQUENCE {
	cause										Cause,
	iE-Extensions								ProtocolExtensionContainer { { GeneralCauseItem-RL-AdditionFailureFDD-ExtIEs} }			OPTIONAL,
	...
}

GeneralCauseItem-RL-AdditionFailureFDD-ExtIEs  NBAP-PROTOCOL-EXTENSION ::= {
	...
}

RLSpecificCauseList-RL-AdditionFailureFDD ::= SEQUENCE {
	unsuccessful-RL-InformationRespList-RL-AdditionFailureFDD		Unsuccessful-RL-InformationRespList-RL-AdditionFailureFDD,
	successful-RL-InformationRespList-RL-AdditionFailureFDD			Successful-RL-InformationRespList-RL-AdditionFailureFDD  OPTIONAL,
	iE-Extensions								ProtocolExtensionContainer { { RLSpecificCauseItem-RL-AdditionFailureFDD-ExtIEs} }			OPTIONAL,
	...
}

RLSpecificCauseItem-RL-AdditionFailureFDD-ExtIEs  NBAP-PROTOCOL-EXTENSION ::= {
	...
}

Unsuccessful-RL-InformationRespList-RL-AdditionFailureFDD ::= SEQUENCE	(SIZE (1..maxNrOfRLs-1)) OF ProtocolIE-Single-Container {{ Unsuccessful-RL-InformationRespItemIE-RL-AdditionFailureFDD }}

Unsuccessful-RL-InformationRespItemIE-RL-AdditionFailureFDD NBAP-PROTOCOL-IES ::= {
	{ ID	id-Unsuccessful-RL-InformationRespItem-RL-AdditionFailureFDD		CRITICALITY		ignore		TYPE	Unsuccessful-RL-InformationRespItem-RL-AdditionFailureFDD	PRESENCE	mandatory}
}

Unsuccessful-RL-InformationRespItem-RL-AdditionFailureFDD ::= SEQUENCE {
	rL-ID										RL-ID,
	cause										Cause,
	iE-Extensions								ProtocolExtensionContainer { { Unsuccessful-RL-InformationRespItem-RL-AdditionFailureFDD-ExtIEs} }			OPTIONAL,
	...
}

Unsuccessful-RL-InformationRespItem-RL-AdditionFailureFDD-ExtIEs  NBAP-PROTOCOL-EXTENSION ::= {
	...
}

Successful-RL-InformationRespList-RL-AdditionFailureFDD ::= SEQUENCE (SIZE (1..maxNrOfRLs-2)) OF ProtocolIE-Single-Container {{ Successful-RL-InformationRespItemIE-RL-AdditionFailureFDD }}

Successful-RL-InformationRespItemIE-RL-AdditionFailureFDD NBAP-PROTOCOL-IES ::= {
	{ ID	id-Successful-RL-InformationRespItem-RL-AdditionFailureFDD		CRITICALITY		ignore		TYPE	Successful-RL-InformationRespItem-RL-AdditionFailureFDD		PRESENCE	mandatory}
}

Successful-RL-InformationRespItem-RL-AdditionFailureFDD ::= SEQUENCE {
	rL-ID										RL-ID,
	rL-Set-ID									RL-Set-ID,
	received-total-wide-band-power				Received-total-wide-band-power-Value,
	diversityIndication							DiversityIndication-RL-AdditionFailureFDD,
	sSDT-SupportIndicator						SSDT-SupportIndicator,
	iE-Extensions								ProtocolExtensionContainer { { Successful-RL-InformationRespItem-RL-AdditionFailureFDD-ExtIEs} }		OPTIONAL,
	...
}

Successful-RL-InformationRespItem-RL-AdditionFailureFDD-ExtIEs  NBAP-PROTOCOL-EXTENSION ::= {
	{ ID id-DL-PowerBalancing-ActivationIndicator	CRITICALITY ignore		EXTENSION		DL-PowerBalancing-ActivationIndicator		PRESENCE optional},
	...
}

DiversityIndication-RL-AdditionFailureFDD ::= CHOICE {
 	combining						Combining-RL-AdditionFailureFDD,
 	non-Combining					Non-Combining-RL-AdditionFailureFDD
}

Combining-RL-AdditionFailureFDD ::= SEQUENCE {
 	rL-ID										RL-ID,
	iE-Extensions								ProtocolExtensionContainer { { CombiningItem-RL-AdditionFailureFDD-ExtIEs} }			OPTIONAL,
	...
 }

CombiningItem-RL-AdditionFailureFDD-ExtIEs NBAP-PROTOCOL-EXTENSION ::= {
	...
}

Non-Combining-RL-AdditionFailureFDD ::= SEQUENCE {
 	dCH-InformationResponse						DCH-InformationResponse,
	iE-Extensions									ProtocolExtensionContainer { { Non-CombiningItem-RL-AdditionFailureFDD-ExtIEs} }			OPTIONAL,
	...
}

Non-CombiningItem-RL-AdditionFailureFDD-ExtIEs NBAP-PROTOCOL-EXTENSION ::= {
	...
}

-- **************************************************************
--
-- RADIO LINK ADDITION FAILURE TDD
--
-- **************************************************************

RadioLinkAdditionFailureTDD ::= SEQUENCE {
	protocolIEs				ProtocolIE-Container	{{RadioLinkAdditionFailureTDD-IEs}},
	protocolExtensions		ProtocolExtensionContainer	{{RadioLinkAdditionFailureTDD-Extensions}}		OPTIONAL,
	...
}

RadioLinkAdditionFailureTDD-IEs NBAP-PROTOCOL-IES ::= {
	{ ID	id-CRNC-CommunicationContextID				CRITICALITY		ignore		TYPE	CRNC-CommunicationContextID									PRESENCE 	mandatory	}|
	{ ID    id-CauseLevel-RL-AdditionFailureTDD			CRITICALITY		ignore		TYPE	CauseLevel-RL-AdditionFailureTDD							PRESENCE	mandatory }|
	{ ID	id-CriticalityDiagnostics					CRITICALITY		ignore		TYPE	CriticalityDiagnostics										PRESENCE	optional	},
	...
}

RadioLinkAdditionFailureTDD-Extensions NBAP-PROTOCOL-EXTENSION ::= {
	...
}

CauseLevel-RL-AdditionFailureTDD ::= CHOICE {
	generalCause		GeneralCauseList-RL-AdditionFailureTDD,
	rLSpecificCause		RLSpecificCauseList-RL-AdditionFailureTDD,
	...
}

GeneralCauseList-RL-AdditionFailureTDD ::= SEQUENCE {
	cause						Cause,
	iE-Extensions				ProtocolExtensionContainer { { GeneralCauseItem-RL-AdditionFailureTDD-ExtIEs} }		OPTIONAL,
	...
}

GeneralCauseItem-RL-AdditionFailureTDD-ExtIEs NBAP-PROTOCOL-EXTENSION ::= {
	...
}

RLSpecificCauseList-RL-AdditionFailureTDD ::= SEQUENCE {
	unsuccessful-RL-InformationRespItem-RL-AdditionFailureTDD	Unsuccessful-RL-InformationRespItem-RL-AdditionFailureTDD,
	iE-Extensions												ProtocolExtensionContainer { { RLSpecificCauseItem-RL-AdditionFailureTDD-ExtIEs} }		OPTIONAL,
	...
}

RLSpecificCauseItem-RL-AdditionFailureTDD-ExtIEs NBAP-PROTOCOL-EXTENSION ::= {
	...
}

Unsuccessful-RL-InformationRespItem-RL-AdditionFailureTDD ::= ProtocolIE-Single-Container { {Unsuccessful-RL-InformationRespItemIE-RL-AdditionFailureTDD} }

Unsuccessful-RL-InformationRespItemIE-RL-AdditionFailureTDD NBAP-PROTOCOL-IES ::= {
	{ ID id-Unsuccessful-RL-InformationResp-RL-AdditionFailureTDD	CRITICALITY ignore	TYPE Unsuccessful-RL-InformationResp-RL-AdditionFailureTDD	PRESENCE mandatory }
}

Unsuccessful-RL-InformationResp-RL-AdditionFailureTDD ::= SEQUENCE {
	rL-ID									RL-ID,
	cause									Cause,
	iE-Extensions							ProtocolExtensionContainer { { Unsuccessful-RL-InformationResp-RL-AdditionFailureTDD-ExtIEs} }		OPTIONAL,
	...
}

Unsuccessful-RL-InformationResp-RL-AdditionFailureTDD-ExtIEs  NBAP-PROTOCOL-EXTENSION ::= {
	...
}

-- **************************************************************
--
-- RADIO LINK RECONFIGURATION PREPARE FDD
--
-- **************************************************************

RadioLinkReconfigurationPrepareFDD ::= SEQUENCE {
	protocolIEs				ProtocolIE-Container	{{RadioLinkReconfigurationPrepareFDD-IEs}},
	protocolExtensions		ProtocolExtensionContainer	{{RadioLinkReconfigurationPrepareFDD-Extensions}}		OPTIONAL,
	...
}

RadioLinkReconfigurationPrepareFDD-IEs NBAP-PROTOCOL-IES ::= {
	{ ID	id-NodeB-CommunicationContextID					CRITICALITY		reject			TYPE	NodeB-CommunicationContextID				PRESENCE	mandatory	} |
	{ ID	id-UL-DPCH-Information-RL-ReconfPrepFDD			CRITICALITY		reject			TYPE	UL-DPCH-Information-RL-ReconfPrepFDD		PRESENCE	optional	} |
	{ ID	id-DL-DPCH-Information-RL-ReconfPrepFDD			CRITICALITY		reject			TYPE	DL-DPCH-Information-RL-ReconfPrepFDD		PRESENCE	optional	} |
	{ ID	id-FDD-DCHs-to-Modify				CRITICALITY		reject			TYPE	FDD-DCHs-to-Modify				PRESENCE	optional	} |
	{ ID	id-DCHs-to-Add-FDD					CRITICALITY		reject			TYPE	DCH-FDD-Information				PRESENCE	optional	} |
	{ ID	id-DCH-DeleteList-RL-ReconfPrepFDD				CRITICALITY		reject			TYPE	DCH-DeleteList-RL-ReconfPrepFDD				PRESENCE	optional	} |
	{ ID	id-DSCH-ModifyList-RL-ReconfPrepFDD				CRITICALITY		reject			TYPE	DSCH-ModifyList-RL-ReconfPrepFDD				PRESENCE	optional	} |
	{ ID	id-DSCHs-to-Add-FDD				CRITICALITY		reject			TYPE	DSCH-FDD-Information					PRESENCE	optional	} |
	{ ID	id-DSCH-DeleteList-RL-ReconfPrepFDD				CRITICALITY		reject			TYPE	DSCH-DeleteList-RL-ReconfPrepFDD				PRESENCE	optional	} |
	{ ID	id-TFCI2-BearerSpecificInformation-RL-ReconfPrepFDD		CRITICALITY		reject		TYPE	TFCI2-BearerSpecificInformation-RL-ReconfPrepFDD
	PRESENCE optional } |
	{ ID	id-RL-InformationList-RL-ReconfPrepFDD			CRITICALITY		reject			TYPE	RL-InformationList-RL-ReconfPrepFDD			PRESENCE	optional	}|
	{ ID id-Transmission-Gap-Pattern-Sequence-Information	CRITICALITY 	reject			TYPE Transmission-Gap-Pattern-Sequence-Information	 PRESENCE optional },
	...
}

RadioLinkReconfigurationPrepareFDD-Extensions NBAP-PROTOCOL-EXTENSION ::= {
	{ ID id-DSCH-FDD-Common-Information					CRITICALITY ignore	EXTENSION DSCH-FDD-Common-Information						PRESENCE optional	}|
	{ ID id-SignallingBearerRequestIndicator	CRITICALITY reject	EXTENSION	SignallingBearerRequestIndicator					PRESENCE optional	}|
	{ ID	id-HSDSCH-Information-to-Modify			CRITICALITY reject		EXTENSION HSDSCH-Information-to-Modify				PRESENCE optional	}|
	{ ID	id-HSDSCH-FDD-Information-to-Add		CRITICALITY reject		EXTENSION HSDSCH-FDD-Information				PRESENCE optional	}|
	{ ID	id-HSDSCH-FDD-Information-to-Delete		CRITICALITY reject		EXTENSION HSDSCH-DeleteList-RL-ReconfPrepFDD		PRESENCE optional	}|
	{ ID	id-HSDSCH-RNTI							CRITICALITY reject		EXTENSION HSDSCH-RNTI				PRESENCE optional	}|
	{ ID	id-HSPDSCH-RL-ID						CRITICALITY reject		EXTENSION RL-ID						PRESENCE optional	},
	...
}

UL-DPCH-Information-RL-ReconfPrepFDD ::= SEQUENCE {
	ul-ScramblingCode								UL-ScramblingCode					OPTIONAL,
	ul-SIR-Target									UL-SIR								OPTIONAL,
	minUL-ChannelisationCodeLength					MinUL-ChannelisationCodeLength		OPTIONAL,
	maxNrOfUL-DPDCHs								MaxNrOfUL-DPDCHs					OPTIONAL,
	-- This IE shall be present if minUL-ChannelisationCodeLength Ie is set to 4 
	ul-PunctureLimit								PunctureLimit						OPTIONAL,
	tFCS											TFCS		OPTIONAL,
	ul-DPCCH-SlotFormat								UL-DPCCH-SlotFormat					OPTIONAL,
	diversityMode									DiversityMode						OPTIONAL,
	sSDT-CellIDLength								SSDT-CellID-Length					OPTIONAL,
	s-FieldLength									S-FieldLength						OPTIONAL,
	iE-Extensions									ProtocolExtensionContainer { { UL-DPCH-Information-RL-ReconfPrepFDD-ExtIEs} }		OPTIONAL,
	...
}

UL-DPCH-Information-RL-ReconfPrepFDD-ExtIEs  NBAP-PROTOCOL-EXTENSION ::= {
	...
}

DL-DPCH-Information-RL-ReconfPrepFDD ::= SEQUENCE {
	tFCS											TFCS								OPTIONAL,
	dl-DPCH-SlotFormat								DL-DPCH-SlotFormat					OPTIONAL,
	tFCI-SignallingMode								TFCI-SignallingMode					OPTIONAL,
	tFCI-Presence									TFCI-Presence						OPTIONAL,
	-- This IE shall be present if the DL DPCH Slot Format IE is set to any of the values from 12 to 16
	multiplexingPosition							MultiplexingPosition 				OPTIONAL,
	pDSCH-CodeMapping								PDSCH-CodeMapping					OPTIONAL,
	pDSCH-RL-ID										RL-ID								OPTIONAL,
	limitedPowerIncrease							LimitedPowerIncrease				OPTIONAL,
	iE-Extensions									ProtocolExtensionContainer { { DL-DPCH-Information-RL-ReconfPrepFDD-ExtIEs} }		OPTIONAL,
	...
}

DL-DPCH-Information-RL-ReconfPrepFDD-ExtIEs  NBAP-PROTOCOL-EXTENSION ::= {
	...
}

DCH-DeleteList-RL-ReconfPrepFDD ::= SEQUENCE (SIZE (1..maxNrOfDCHs)) OF DCH-DeleteItem-RL-ReconfPrepFDD

DCH-DeleteItem-RL-ReconfPrepFDD ::= SEQUENCE {
	dCH-ID											DCH-ID,
	iE-Extensions									ProtocolExtensionContainer { { DCH-DeleteItem-RL-ReconfPrepFDD-ExtIEs} }		OPTIONAL,
	...
}

DCH-DeleteItem-RL-ReconfPrepFDD-ExtIEs  NBAP-PROTOCOL-EXTENSION ::= {
	...
}

DSCH-ModifyList-RL-ReconfPrepFDD ::= SEQUENCE (SIZE (1..maxNrOfDSCHs)) OF ProtocolIE-Single-Container {{DSCH-ModifyItemIE-RL-ReconfPrepFDD }}

DSCH-ModifyItemIE-RL-ReconfPrepFDD NBAP-PROTOCOL-IES ::= {
	{ ID	id-DSCH-ModifyItem-RL-ReconfPrepFDD		CRITICALITY	reject		TYPE	DSCH-ModifyItem-RL-ReconfPrepFDD	PRESENCE	mandatory}
}

DSCH-ModifyItem-RL-ReconfPrepFDD ::= SEQUENCE {
	dSCH-ID											DSCH-ID,
	dl-TransportFormatSet							TransportFormatSet			OPTIONAL,
	allocationRetentionPriority						AllocationRetentionPriority	OPTIONAL,
	frameHandlingPriority							FrameHandlingPriority		OPTIONAL,
	toAWS											ToAWS						OPTIONAL,
	toAWE											ToAWE						OPTIONAL,
	transportBearerRequestIndicator					TransportBearerRequestIndicator,
	iE-Extensions									ProtocolExtensionContainer { { DSCH-ModifyItem-RL-ReconfPrepFDD-ExtIEs} }		OPTIONAL,
	...
}

DSCH-ModifyItem-RL-ReconfPrepFDD-ExtIEs  NBAP-PROTOCOL-EXTENSION ::= {
	{ ID	id-bindingID						CRITICALITY	ignore		EXTENSION 	BindingID		PRESENCE 	optional	}|
	{ ID	id-transportlayeraddress			CRITICALITY	ignore		EXTENSION 	TransportLayerAddress		PRESENCE 	optional	},
	...
}

DSCH-DeleteList-RL-ReconfPrepFDD ::= SEQUENCE (SIZE (1..maxNrOfDSCHs)) OF ProtocolIE-Single-Container {{DSCH-DeleteItemIE-RL-ReconfPrepFDD }}

DSCH-DeleteItemIE-RL-ReconfPrepFDD NBAP-PROTOCOL-IES ::= {
	{ ID	id-DSCH-DeleteItem-RL-ReconfPrepFDD		CRITICALITY	reject		TYPE	DSCH-DeleteItem-RL-ReconfPrepFDD	PRESENCE	mandatory}
}

DSCH-DeleteItem-RL-ReconfPrepFDD ::= SEQUENCE {
	dSCH-ID											DSCH-ID,
	iE-Extensions									ProtocolExtensionContainer { { DSCH-DeleteItem-RL-ReconfPrepFDD-ExtIEs} }		OPTIONAL,
	...
}

DSCH-DeleteItem-RL-ReconfPrepFDD-ExtIEs  NBAP-PROTOCOL-EXTENSION ::= {
	...
}

TFCI2-BearerSpecificInformation-RL-ReconfPrepFDD ::= CHOICE {
	addOrModify				AddOrModify-TFCI2-RL-ReconfPrepFDD,
	delete					NULL
}

AddOrModify-TFCI2-RL-ReconfPrepFDD ::= SEQUENCE {
	toAWS								ToAWS,
	toAWE								ToAWE,
	iE-Extensions						ProtocolExtensionContainer { { AddOrModify-TFCI2-RL-ReconfPrepFDD-ExtIEs} }		OPTIONAL,
	...
}

AddOrModify-TFCI2-RL-ReconfPrepFDD-ExtIEs  NBAP-PROTOCOL-EXTENSION ::= {
	{ ID id-TFCI2BearerRequestIndicator		CRITICALITY		reject			EXTENSION	TFCI2BearerRequestIndicator			PRESENCE	optional }|
	{ ID id-bindingID						CRITICALITY		ignore			EXTENSION 	BindingID			PRESENCE 	optional	}|
	{ ID id-transportlayeraddress			CRITICALITY		ignore			EXTENSION 	TransportLayerAddress			PRESENCE 	optional	},
	...
}

RL-InformationList-RL-ReconfPrepFDD ::= SEQUENCE (SIZE (1..maxNrOfRLs)) OF ProtocolIE-Single-Container {{ RL-InformationItemIE-RL-ReconfPrepFDD }}

RL-InformationItemIE-RL-ReconfPrepFDD NBAP-PROTOCOL-IES ::= {
	{ ID	id-RL-InformationItem-RL-ReconfPrepFDD			CRITICALITY		reject			TYPE 	RL-InformationItem-RL-ReconfPrepFDD		PRESENCE	mandatory}
}

RL-InformationItem-RL-ReconfPrepFDD ::= SEQUENCE {
	rL-ID											RL-ID,
	dl-CodeInformation							FDD-DL-CodeInformation		OPTIONAL,
	maxDL-Power										DL-Power									OPTIONAL,
	minDL-Power										DL-Power									OPTIONAL,
	sSDT-Indication									SSDT-Indication								OPTIONAL,
	sSDT-Cell-Identity								SSDT-Cell-Identity							OPTIONAL,
	-- The IE shall be present if the SSDT Indication IE is set to “SSDT Active in the UE”
	transmitDiversityIndicator						TransmitDiversityIndicator					OPTIONAL,
	-- This IE shall be present if Diversity Mode IE is present in UL DPCH Information IE and it is not set to “none”
	iE-Extensions									ProtocolExtensionContainer { { RL-InformationItem-RL-ReconfPrepFDD-ExtIEs} }		OPTIONAL,
	...
}

RL-InformationItem-RL-ReconfPrepFDD-ExtIEs  NBAP-PROTOCOL-EXTENSION ::= {
	{ ID id-SSDT-CellIDforEDSCHPC CRITICALITY ignore EXTENSION SSDT-Cell-Identity 		PRESENCE conditional }|
	-- This IE shall be present if Enhanced DSCH PC IE is present in the DSCH Common Information IE.
	{ ID id-DLReferencePower		CRITICALITY ignore	EXTENSION	DL-Power				PRESENCE optional	}|
	{ ID id-RL-Specific-DCH-Info		CRITICALITY	ignore		EXTENSION 	RL-Specific-DCH-Info	PRESENCE 	optional	}|
	{ ID id-DL-DPCH-TimingAdjustment CRITICALITY reject EXTENSION DL-DPCH-TimingAdjustment 	PRESENCE optional }|
	{ ID id-Qth-Parameter	CRITICALITY ignore		EXTENSION	Qth-Parameter 		PRESENCE optional },
	...
}

HSDSCH-DeleteList-RL-ReconfPrepFDD ::= SEQUENCE (SIZE (1..maxNrOfMACdFlows)) OF HSDSCH-DeleteItem-RL-ReconfPrepFDD

HSDSCH-DeleteItem-RL-ReconfPrepFDD ::= SEQUENCE {
	hsDSCH-MACdFlow-ID								HSDSCH-MACdFlow-ID,
	iE-Extensions									ProtocolExtensionContainer { { HSDSCH-DeleteItem-RL-ReconfPrepFDD-ExtIEs} }		OPTIONAL,
	...
}

HSDSCH-DeleteItem-RL-ReconfPrepFDD-ExtIEs  NBAP-PROTOCOL-EXTENSION ::= {
	...
}

-- **************************************************************
--
-- RADIO LINK RECONFIGURATION PREPARE TDD
--
-- **************************************************************

RadioLinkReconfigurationPrepareTDD ::= SEQUENCE {
	protocolIEs				ProtocolIE-Container	{{RadioLinkReconfigurationPrepareTDD-IEs}},
	protocolExtensions		ProtocolExtensionContainer	{{RadioLinkReconfigurationPrepareTDD-Extensions}}		OPTIONAL,
	...
}

RadioLinkReconfigurationPrepareTDD-IEs NBAP-PROTOCOL-IES ::= {
	{ ID	id-NodeB-CommunicationContextID							CRITICALITY		reject		TYPE	NodeB-CommunicationContextID						PRESENCE 	mandatory	}|
	{ ID	id-UL-CCTrCH-InformationAddList-RL-ReconfPrepTDD			CRITICALITY		reject		TYPE	UL-CCTrCH-InformationAddList-RL-ReconfPrepTDD			PRESENCE	optional		} |
	{ ID	id-UL-CCTrCH-InformationModifyList-RL-ReconfPrepTDD			CRITICALITY		reject		TYPE	UL-CCTrCH-InformationModifyList-RL-ReconfPrepTDD			PRESENCE	optional		} |
	{ ID	id-UL-CCTrCH-InformationDeleteList-RL-ReconfPrepTDD			CRITICALITY		reject		TYPE	UL-CCTrCH-InformationDeleteList-RL-ReconfPrepTDD			PRESENCE	optional		} |
	{ ID	id-DL-CCTrCH-InformationAddList-RL-ReconfPrepTDD			CRITICALITY 	reject		TYPE 	DL-CCTrCH-InformationAddList-RL-ReconfPrepTDD			PRESENCE	optional		} |
	{ ID	id-DL-CCTrCH-InformationModifyList-RL-ReconfPrepTDD			CRITICALITY 	reject		TYPE 	DL-CCTrCH-InformationModifyList-RL-ReconfPrepTDD			PRESENCE	optional		} |
	{ ID	id-DL-CCTrCH-InformationDeleteList-RL-ReconfPrepTDD			CRITICALITY 	reject		TYPE 	DL-CCTrCH-InformationDeleteList-RL-ReconfPrepTDD			PRESENCE	optional		} |
	{ ID	id-TDD-DCHs-to-Modify						CRITICALITY		reject		TYPE	TDD-DCHs-to-Modify						PRESENCE	optional		} |
	{ ID	id-DCHs-to-Add-TDD							CRITICALITY		reject		TYPE	DCH-TDD-Information						PRESENCE	optional		} |
	{ ID	id-DCH-DeleteList-RL-ReconfPrepTDD						CRITICALITY		reject		TYPE	DCH-DeleteList-RL-ReconfPrepTDD						PRESENCE	optional		} |
	{ ID	id-DSCH-Information-ModifyList-RL-ReconfPrepTDD			CRITICALITY		reject		TYPE	DSCH-Information-ModifyList-RL-ReconfPrepTDD		PRESENCE	optional		} |
	{ ID	id-DSCHs-to-Add-TDD			CRITICALITY		reject		TYPE 	DSCH-TDD-Information			PRESENCE 	optional		} |
	{ ID	id-DSCH-Information-DeleteList-RL-ReconfPrepTDD			CRITICALITY 	reject		TYPE	DSCH-Information-DeleteList-RL-ReconfPrepTDD		PRESENCE 	optional		} |
	{ ID	id-USCH-Information-ModifyList-RL-ReconfPrepTDD			CRITICALITY		reject		TYPE	USCH-Information-ModifyList-RL-ReconfPrepTDD		PRESENCE 	optional		} |
	{ ID	id-USCH-Information-Add			CRITICALITY		reject		TYPE	USCH-Information			PRESENCE 	optional		} |
	{ ID	id-USCH-Information-DeleteList-RL-ReconfPrepTDD			CRITICALITY 	reject		TYPE	USCH-Information-DeleteList-RL-ReconfPrepTDD		PRESENCE	optional		} |
	{ ID	id-RL-Information-RL-ReconfPrepTDD						CRITICALITY		reject		TYPE	RL-Information-RL-ReconfPrepTDD						PRESENCE 	optional		},
	...
}

RadioLinkReconfigurationPrepareTDD-Extensions NBAP-PROTOCOL-EXTENSION ::= {
	{ ID id-SignallingBearerRequestIndicator	CRITICALITY reject	EXTENSION	SignallingBearerRequestIndicator					PRESENCE optional	}|
	{ ID	id-HSDSCH-Information-to-Modify			CRITICALITY reject		EXTENSION HSDSCH-Information-to-Modify				PRESENCE optional	}|
	{ ID	id-HSDSCH-TDD-Information-to-Add		CRITICALITY reject		EXTENSION HSDSCH-TDD-Information				PRESENCE optional	}|
	{ ID	id-HSDSCH-TDD-Information-to-Delete		CRITICALITY reject		EXTENSION HSDSCH-DeleteList-RL-ReconfPrepTDD		PRESENCE optional	}|
	{ ID	id-HSDSCH-RNTI							CRITICALITY reject		EXTENSION HSDSCH-RNTI				PRESENCE optional	}|
	{ ID	id-HSPDSCH-RL-ID						CRITICALITY reject		EXTENSION RL-ID						PRESENCE optional	}|
	{ ID 	id-PDSCH-RL-ID							CRITICALITY ignore		EXTENSION RL-ID						PRESENCE optional },
	...
}

UL-CCTrCH-InformationAddList-RL-ReconfPrepTDD ::= SEQUENCE (SIZE (1..maxNrOfCCTrCHs)) OF UL-CCTrCH-InformationAddItem-RL-ReconfPrepTDD

UL-CCTrCH-InformationAddItem-RL-ReconfPrepTDD ::= SEQUENCE {
	cCTrCH-ID									CCTrCH-ID,
	tFCS										TFCS,
	tFCI-Coding									TFCI-Coding,
	punctureLimit								PunctureLimit,
	ul-DPCH-InformationList						UL-DPCH-InformationAddList-RL-ReconfPrepTDD	OPTIONAL,
	iE-Extensions								ProtocolExtensionContainer { { UL-CCTrCH-InformationAddItem-RL-ReconfPrepTDD-ExtIEs} }		OPTIONAL,
	...
}

UL-CCTrCH-InformationAddItem-RL-ReconfPrepTDD-ExtIEs  NBAP-PROTOCOL-EXTENSION ::= {
	{ ID id-UL-DPCH-LCR-InformationAddListIE-RL-ReconfPrepTDD   CRITICALITY reject		EXTENSION UL-DPCH-LCR-InformationAddList-RL-ReconfPrepTDD		PRESENCE optional }|	-- Applicable to 1.28Mcps TDD only
	{ ID id-UL-SIRTarget		CRITICALITY reject		EXTENSION		UL-SIR		PRESENCE optional	},
	-- Mandatory for 1.28Mcps TDD, Not Applicable to 3.84Mcps TDD.
	...
}

UL-DPCH-InformationAddList-RL-ReconfPrepTDD ::= ProtocolIE-Single-Container {{ UL-DPCH-InformationAddListIEs-RL-ReconfPrepTDD }}

UL-DPCH-InformationAddListIEs-RL-ReconfPrepTDD NBAP-PROTOCOL-IES ::= {
	{ ID id-UL-DPCH-InformationAddListIE-RL-ReconfPrepTDD   CRITICALITY reject		TYPE UL-DPCH-InformationAddItem-RL-ReconfPrepTDD		PRESENCE mandatory }
}

UL-DPCH-InformationAddItem-RL-ReconfPrepTDD ::= SEQUENCE {
	repetitionPeriod						RepetitionPeriod,
	repetitionLength						RepetitionLength,
	tdd-DPCHOffset							TDD-DPCHOffset,
	uL-Timeslot-Information					UL-Timeslot-Information,
	iE-Extensions							ProtocolExtensionContainer { { UL-DPCH-InformationAddItem-RL-ReconfPrepTDD-ExtIEs} }		OPTIONAL,
	...
}

UL-DPCH-InformationAddItem-RL-ReconfPrepTDD-ExtIEs  NBAP-PROTOCOL-EXTENSION ::= {
	...
}

UL-DPCH-LCR-InformationAddList-RL-ReconfPrepTDD ::= SEQUENCE {
	repetitionPeriod						RepetitionPeriod,
	repetitionLength						RepetitionLength,
	tdd-DPCHOffset							TDD-DPCHOffset,
	uL-Timeslot-InformationLCR				UL-TimeslotLCR-Information,
	iE-Extensions							ProtocolExtensionContainer { { UL-DPCH-LCR-InformationAddItem-RL-ReconfPrepTDD-ExtIEs} }		OPTIONAL,
	...
}

UL-DPCH-LCR-InformationAddItem-RL-ReconfPrepTDD-ExtIEs  NBAP-PROTOCOL-EXTENSION ::= {
	...
}

UL-CCTrCH-InformationModifyList-RL-ReconfPrepTDD ::= SEQUENCE (SIZE (1..maxNrOfCCTrCHs)) OF UL-CCTrCH-InformationModifyItem-RL-ReconfPrepTDD

UL-CCTrCH-InformationModifyItem-RL-ReconfPrepTDD ::= SEQUENCE {
	cCTrCH-ID									CCTrCH-ID,
	tFCS										TFCS														OPTIONAL,
	tFCI-Coding									TFCI-Coding													OPTIONAL,
	punctureLimit								PunctureLimit 												OPTIONAL,
	ul-DPCH-InformationAddList					UL-DPCH-InformationModify-AddList-RL-ReconfPrepTDD		OPTIONAL,
	ul-DPCH-InformationModifyList				UL-DPCH-InformationModify-ModifyList-RL-ReconfPrepTDD	OPTIONAL,
	ul-DPCH-InformationDeleteList				UL-DPCH-InformationModify-DeleteList-RL-ReconfPrepTDD	OPTIONAL,
	iE-Extensions								ProtocolExtensionContainer { { UL-CCTrCH-InformationModifyItem-RL-ReconfPrepTDD-ExtIEs} }		OPTIONAL,
	...
}

UL-CCTrCH-InformationModifyItem-RL-ReconfPrepTDD-ExtIEs  NBAP-PROTOCOL-EXTENSION ::= {
	{ ID id-UL-DPCH-LCR-InformationModify-AddList	 CRITICALITY reject		EXTENSION	 UL-DPCH-LCR-InformationModify-AddList-RL-ReconfPrepTDD		PRESENCE optional }|	-- Applicable to 1.28Mcps TDD only
	{ ID id-UL-SIRTarget		CRITICALITY reject		EXTENSION		UL-SIR		PRESENCE optional	},
	-- Applicable to 1.28Mcps TDD only.
	...
}

UL-DPCH-InformationModify-AddList-RL-ReconfPrepTDD ::= ProtocolIE-Single-Container {{ UL-DPCH-InformationModify-AddListIEs-RL-ReconfPrepTDD }}

UL-DPCH-InformationModify-AddListIEs-RL-ReconfPrepTDD NBAP-PROTOCOL-IES ::= {
	{ ID id-UL-DPCH-InformationModify-AddListIE-RL-ReconfPrepTDD   CRITICALITY reject		TYPE UL-DPCH-InformationModify-AddItem-RL-ReconfPrepTDD		PRESENCE mandatory }
}

UL-DPCH-InformationModify-AddItem-RL-ReconfPrepTDD ::= SEQUENCE {
	repetitionPeriod						RepetitionPeriod,
	repetitionLength						RepetitionLength,
	tdd-DPCHOffset							TDD-DPCHOffset,
	uL-Timeslot-Information				UL-Timeslot-Information,
	iE-Extensions								ProtocolExtensionContainer { { UL-DPCH-InformationModify-AddItem-RL-ReconfPrepTDD-ExtIEs} }		OPTIONAL,
	...
}

UL-DPCH-InformationModify-AddItem-RL-ReconfPrepTDD-ExtIEs  NBAP-PROTOCOL-EXTENSION ::= {
	...
}

UL-DPCH-LCR-InformationModify-AddList-RL-ReconfPrepTDD ::= SEQUENCE {
	repetitionPeriod						RepetitionPeriod,
	repetitionLength						RepetitionLength,
	tdd-DPCHOffset							TDD-DPCHOffset,
	uL-Timeslot-InformationLCR				UL-TimeslotLCR-Information,
	iE-Extensions								ProtocolExtensionContainer { { UL-DPCH-LCR-InformationModify-AddItem-RL-ReconfPrepTDD-ExtIEs} }		OPTIONAL,
	...
}

UL-DPCH-LCR-InformationModify-AddItem-RL-ReconfPrepTDD-ExtIEs  NBAP-PROTOCOL-EXTENSION ::= {
	...
}

UL-DPCH-InformationModify-ModifyList-RL-ReconfPrepTDD ::= ProtocolIE-Single-Container {{ UL-DPCH-InformationModify-ModifyListIEs-RL-ReconfPrepTDD }}

UL-DPCH-InformationModify-ModifyListIEs-RL-ReconfPrepTDD NBAP-PROTOCOL-IES ::= {
	{ ID id-UL-DPCH-InformationModify-ModifyListIE-RL-ReconfPrepTDD   CRITICALITY reject		TYPE UL-DPCH-InformationModify-ModifyItem-RL-ReconfPrepTDD		PRESENCE mandatory }
}

UL-DPCH-InformationModify-ModifyItem-RL-ReconfPrepTDD ::= SEQUENCE {
	repetitionPeriod						RepetitionPeriod	OPTIONAL,
	repetitionLength						RepetitionLength	OPTIONAL,
	tdd-DPCHOffset							TDD-DPCHOffset		OPTIONAL,
	uL-Timeslot-InformationModify-ModifyList-RL-ReconfPrepTDD				UL-Timeslot-InformationModify-ModifyList-RL-ReconfPrepTDD			OPTIONAL,
	iE-Extensions								ProtocolExtensionContainer { { UL-DPCH-InformationModify-ModifyItem-RL-ReconfPrepTDD-ExtIEs} }		OPTIONAL,
	...
}

UL-DPCH-InformationModify-ModifyItem-RL-ReconfPrepTDD-ExtIEs  NBAP-PROTOCOL-EXTENSION ::= {
	{ ID id-UL-TimeslotLCR-Information-RL-ReconfPrepTDD   	CRITICALITY reject		EXTENSION 	UL-TimeslotLCR-InformationModify-ModifyList-RL-ReconfPrepTDD		PRESENCE optional },	-- Applicable to 1.28Mcps TDD only
	...
}

UL-Timeslot-InformationModify-ModifyList-RL-ReconfPrepTDD ::= SEQUENCE (SIZE (1..maxNrOfULTSs)) OF UL-Timeslot-InformationModify-ModifyItem-RL-ReconfPrepTDD	-- Applicable to 3.84Mcps TDD only

UL-Timeslot-InformationModify-ModifyItem-RL-ReconfPrepTDD ::= SEQUENCE {
	timeSlot								TimeSlot,
	midambleShiftAndBurstType				MidambleShiftAndBurstType		OPTIONAL,
	tFCI-Presence							TFCI-Presence		OPTIONAL,
	uL-Code-InformationModify-ModifyList-RL-ReconfPrepTDD				UL-Code-InformationModify-ModifyList-RL-ReconfPrepTDD		OPTIONAL,
	iE-Extensions							ProtocolExtensionContainer { { UL-Timeslot-InformationModify-ModifyItem-RL-ReconfPrepTDD-ExtIEs} }		OPTIONAL,
	...
}

UL-Timeslot-InformationModify-ModifyItem-RL-ReconfPrepTDD-ExtIEs NBAP-PROTOCOL-EXTENSION ::= {
	...
}

UL-Code-InformationModify-ModifyList-RL-ReconfPrepTDD ::= SEQUENCE (SIZE (1..maxNrOfDPCHs)) OF UL-Code-InformationModify-ModifyItem-RL-ReconfPrepTDD

UL-Code-InformationModify-ModifyItem-RL-ReconfPrepTDD ::= SEQUENCE {
	dPCH-ID									DPCH-ID,
	tdd-ChannelisationCode					TDD-ChannelisationCode		OPTIONAL,
	iE-Extensions							ProtocolExtensionContainer { { UL-Code-InformationModify-ModifyItem-RL-ReconfPrepTDD-ExtIEs} }		OPTIONAL,
	...
}

UL-Code-InformationModify-ModifyItem-RL-ReconfPrepTDD-ExtIEs NBAP-PROTOCOL-EXTENSION ::= {
	...
}

UL-TimeslotLCR-InformationModify-ModifyList-RL-ReconfPrepTDD ::= SEQUENCE (SIZE (1..maxNrOfULTSLCRs)) OF UL-Timeslot-LCR-InformationModify-ModifyItem-RL-ReconfPrepTDD	-- Applicable to 1.28Mcps TDD only

UL-Timeslot-LCR-InformationModify-ModifyItem-RL-ReconfPrepTDD ::= SEQUENCE {
	timeSlotLCR								TimeSlotLCR,
	midambleShiftLCR			MidambleShiftLCR		OPTIONAL,
	tFCI-Presence							TFCI-Presence		OPTIONAL,
	uL-Code-InformationModify-ModifyList-RL-ReconfPrepTDDLCR				UL-Code-InformationModify-ModifyList-RL-ReconfPrepTDDLCR		OPTIONAL,
	iE-Extensions							ProtocolExtensionContainer { { UL-Timeslot-LCR-InformationModify-ModifyItem-RL-ReconfPrepTDD-ExtIEs} }		OPTIONAL,
	...
}

UL-Timeslot-LCR-InformationModify-ModifyItem-RL-ReconfPrepTDD-ExtIEs NBAP-PROTOCOL-EXTENSION ::= {
	...
}

UL-Code-InformationModify-ModifyList-RL-ReconfPrepTDDLCR ::= SEQUENCE (SIZE (1..maxNrOfDPCHs)) OF UL-Code-InformationModify-ModifyItem-RL-ReconfPrepTDD

UL-Code-InformationModify-ModifyItem-RL-ReconfPrepTDDLCR ::= SEQUENCE {
	dPCH-ID									DPCH-ID,
	tdd-ChannelisationCodeLCR				TDD-ChannelisationCodeLCR		OPTIONAL,
	iE-Extensions							ProtocolExtensionContainer { { UL-Code-InformationModify-ModifyItem-RL-ReconfPrepTDDLCR-ExtIEs} }		OPTIONAL,
	...
}

UL-Code-InformationModify-ModifyItem-RL-ReconfPrepTDDLCR-ExtIEs NBAP-PROTOCOL-EXTENSION ::= {
{ ID id-UL-DPCH-TimeSlotFormat-LCR-ModifyItem-RL-ReconfPrepTDD  CRITICALITY	reject	 EXTENSION TDD-UL-DPCH-TimeSlotFormat-LCR   PRESENCE  optional},

	...
}

UL-DPCH-InformationModify-DeleteList-RL-ReconfPrepTDD ::= ProtocolIE-Single-Container {{ UL-DPCH-InformationModify-DeleteListIEs-RL-ReconfPrepTDD }}

UL-DPCH-InformationModify-DeleteListIEs-RL-ReconfPrepTDD NBAP-PROTOCOL-IES ::= {
	{ ID id-UL-DPCH-InformationModify-DeleteListIE-RL-ReconfPrepTDD   CRITICALITY reject		TYPE UL-DPCH-InformationModify-DeleteListIE-RL-ReconfPrepTDD		PRESENCE mandatory }
}

UL-DPCH-InformationModify-DeleteListIE-RL-ReconfPrepTDD ::= SEQUENCE (SIZE (1..maxNrOfDPCHs)) OF UL-DPCH-InformationModify-DeleteItem-RL-ReconfPrepTDD

UL-DPCH-InformationModify-DeleteItem-RL-ReconfPrepTDD ::= SEQUENCE {
	dPCH-ID										DPCH-ID,
	iE-Extensions								ProtocolExtensionContainer { { UL-DPCH-InformationModify-DeleteItem-RL-ReconfPrepTDD-ExtIEs} }		OPTIONAL,
	...
}

UL-DPCH-InformationModify-DeleteItem-RL-ReconfPrepTDD-ExtIEs  NBAP-PROTOCOL-EXTENSION ::= {
	...
}

UL-CCTrCH-InformationDeleteList-RL-ReconfPrepTDD ::= SEQUENCE (SIZE (1..maxNrOfCCTrCHs)) OF UL-CCTrCH-InformationDeleteItem-RL-ReconfPrepTDD

UL-CCTrCH-InformationDeleteItem-RL-ReconfPrepTDD ::= SEQUENCE {
	cCTrCH-ID									CCTrCH-ID,
	iE-Extensions								ProtocolExtensionContainer { { UL-CCTrCH-InformationDeleteItem-RL-ReconfPrepTDD-ExtIEs} }		OPTIONAL,
	...
}

UL-CCTrCH-InformationDeleteItem-RL-ReconfPrepTDD-ExtIEs  NBAP-PROTOCOL-EXTENSION ::= {
	...
}

DL-CCTrCH-InformationAddList-RL-ReconfPrepTDD ::= SEQUENCE (SIZE (1..maxNrOfCCTrCHs)) OF DL-CCTrCH-InformationAddItem-RL-ReconfPrepTDD

DL-CCTrCH-InformationAddItem-RL-ReconfPrepTDD ::= SEQUENCE {
	cCTrCH-ID										CCTrCH-ID,
	tFCS											TFCS,
	tFCI-Coding										TFCI-Coding,
	punctureLimit									PunctureLimit,
	cCTrCH-TPCList									CCTrCH-TPCAddList-RL-ReconfPrepTDD				OPTIONAL,
	dl-DPCH-InformationList							DL-DPCH-InformationAddList-RL-ReconfPrepTDD 	OPTIONAL,
	iE-Extensions									ProtocolExtensionContainer { { DL-CCTrCH-InformationAddItem-RL-ReconfPrepTDD-ExtIEs} }			OPTIONAL,
	...
}

DL-CCTrCH-InformationAddItem-RL-ReconfPrepTDD-ExtIEs  NBAP-PROTOCOL-EXTENSION ::= {
	{ ID id-DL-DPCH-LCR-InformationAddList-RL-ReconfPrepTDD   CRITICALITY reject		EXTENSION		 DL-DPCH-LCR-InformationAddList-RL-ReconfPrepTDD		PRESENCE optional }|	-- Applicable to 1.28Mcps TDD only
	{ ID id-CCTrCH-Initial-DL-Power-RL-ReconfPrepTDD		CRITICALITY ignore		EXTENSION DL-Power		PRESENCE optional	},
	...
}

CCTrCH-TPCAddList-RL-ReconfPrepTDD ::= SEQUENCE (SIZE (1..maxNrOfCCTrCHs)) OF CCTrCH-TPCAddItem-RL-ReconfPrepTDD		-- Applicable to 3.84Mcps TDD only

CCTrCH-TPCAddItem-RL-ReconfPrepTDD	 ::= SEQUENCE {
	cCTrCH-ID								CCTrCH-ID,
	iE-Extensions							ProtocolExtensionContainer { { CCTrCH-TPCAddItem-RL-ReconfPrepTDD-ExtIEs} }		OPTIONAL,
	...
}

CCTrCH-TPCAddItem-RL-ReconfPrepTDD-ExtIEs  NBAP-PROTOCOL-EXTENSION ::= {
	...
}

DL-DPCH-InformationAddList-RL-ReconfPrepTDD ::= ProtocolIE-Single-Container {{ DL-DPCH-InformationAddListIEs-RL-ReconfPrepTDD }}

DL-DPCH-InformationAddListIEs-RL-ReconfPrepTDD NBAP-PROTOCOL-IES ::= {
	{ ID id-DL-DPCH-InformationAddListIE-RL-ReconfPrepTDD   CRITICALITY reject		TYPE DL-DPCH-InformationAddItem-RL-ReconfPrepTDD		PRESENCE mandatory }
}

DL-DPCH-InformationAddItem-RL-ReconfPrepTDD ::= SEQUENCE {
	repetitionPeriod						RepetitionPeriod,
	repetitionLength						RepetitionLength,
	tdd-DPCHOffset							TDD-DPCHOffset,
	dL-Timeslot-Information					DL-Timeslot-Information,
	iE-Extensions							ProtocolExtensionContainer { { DL-DPCH-InformationAddItem-RL-ReconfPrepTDD-ExtIEs} }		OPTIONAL,
	...
}

DL-DPCH-InformationAddItem-RL-ReconfPrepTDD-ExtIEs  NBAP-PROTOCOL-EXTENSION ::= {
	...
}

DL-DPCH-LCR-InformationAddList-RL-ReconfPrepTDD ::= SEQUENCE {
	repetitionPeriod						RepetitionPeriod,
	repetitionLength						RepetitionLength,
	tdd-DPCHOffset							TDD-DPCHOffset,
	dL-Timeslot-InformationLCR				DL-TimeslotLCR-Information,
	iE-Extensions							ProtocolExtensionContainer { { DL-DPCH-LCR-InformationAddItem-RL-ReconfPrepTDD-ExtIEs} }		OPTIONAL,
	...
}

DL-DPCH-LCR-InformationAddItem-RL-ReconfPrepTDD-ExtIEs  NBAP-PROTOCOL-EXTENSION ::= {
	...
}

DL-CCTrCH-InformationModifyList-RL-ReconfPrepTDD ::= SEQUENCE (SIZE (1..maxNrOfCCTrCHs)) OF DL-CCTrCH-InformationModifyItem-RL-ReconfPrepTDD

DL-CCTrCH-InformationModifyItem-RL-ReconfPrepTDD ::= SEQUENCE {
	cCTrCH-ID										CCTrCH-ID,
	tFCS											TFCS														OPTIONAL,
	tFCI-Coding										TFCI-Coding													OPTIONAL,
	punctureLimit									PunctureLimit 												OPTIONAL,
	cCTrCH-TPCList									CCTrCH-TPCModifyList-RL-ReconfPrepTDD						OPTIONAL,
	dl-DPCH-InformationAddList						DL-DPCH-InformationModify-AddList-RL-ReconfPrepTDD 		OPTIONAL,
	dl-DPCH-InformationModifyList					DL-DPCH-InformationModify-ModifyList-RL-ReconfPrepTDD 	OPTIONAL,
	dl-DPCH-InformationDeleteList					DL-DPCH-InformationModify-DeleteList-RL-ReconfPrepTDD 	OPTIONAL,
	iE-Extensions									ProtocolExtensionContainer { { DL-CCTrCH-InformationModifyItem-RL-ReconfPrepTDD-ExtIEs} }			OPTIONAL,
	...
}

DL-CCTrCH-InformationModifyItem-RL-ReconfPrepTDD-ExtIEs  NBAP-PROTOCOL-EXTENSION ::= {
	{ ID id-DL-DPCH-LCR-InformationModify-AddList-RL-ReconfPrepTDD CRITICALITY reject		EXTENSION 	DL-DPCH-LCR-InformationModify-AddList-RL-ReconfPrepTDD		PRESENCE optional },
	...
}

CCTrCH-TPCModifyList-RL-ReconfPrepTDD ::= SEQUENCE (SIZE (1..maxNrOfCCTrCHs)) OF CCTrCH-TPCModifyItem-RL-ReconfPrepTDD

CCTrCH-TPCModifyItem-RL-ReconfPrepTDD	 ::= SEQUENCE {
	cCTrCH-ID								CCTrCH-ID,
	iE-Extensions							ProtocolExtensionContainer { { CCTrCH-TPCModifyItem-RL-ReconfPrepTDD-ExtIEs} }		OPTIONAL,
	...
}

CCTrCH-TPCModifyItem-RL-ReconfPrepTDD-ExtIEs  NBAP-PROTOCOL-EXTENSION ::= {
	...
}

DL-DPCH-InformationModify-AddList-RL-ReconfPrepTDD ::= ProtocolIE-Single-Container {{ DL-DPCH-InformationModify-AddListIEs-RL-ReconfPrepTDD }}	
-- Applicable to 3.84Mcps TDD only

DL-DPCH-InformationModify-AddListIEs-RL-ReconfPrepTDD NBAP-PROTOCOL-IES ::= {
	{ ID id-DL-DPCH-InformationModify-AddListIE-RL-ReconfPrepTDD   CRITICALITY reject		TYPE DL-DPCH-InformationModify-AddItem-RL-ReconfPrepTDD		PRESENCE mandatory }
}

DL-DPCH-InformationModify-AddItem-RL-ReconfPrepTDD ::= SEQUENCE {
	repetitionPeriod						RepetitionPeriod,
	repetitionLength						RepetitionLength,
	tdd-DPCHOffset							TDD-DPCHOffset,
	dL-Timeslot-Information					DL-Timeslot-Information,
	iE-Extensions							ProtocolExtensionContainer { { DL-DPCH-InformationModify-AddItem-RL-ReconfPrepTDD-ExtIEs} }		OPTIONAL,
	...
}

DL-DPCH-InformationModify-AddItem-RL-ReconfPrepTDD-ExtIEs  NBAP-PROTOCOL-EXTENSION ::= {
	...
}

DL-DPCH-LCR-InformationModify-AddList-RL-ReconfPrepTDD ::= SEQUENCE {
	repetitionPeriod						RepetitionPeriod,
	repetitionLength						RepetitionLength,
	tdd-DPCHOffset							TDD-DPCHOffset,
	dL-Timeslot-InformationLCR				DL-TimeslotLCR-Information,
	iE-Extensions							ProtocolExtensionContainer { { DL-DPCH-LCR-InformationModify-AddItem-RL-ReconfPrepTDD-ExtIEs} }		OPTIONAL,
	...
}

DL-DPCH-LCR-InformationModify-AddItem-RL-ReconfPrepTDD-ExtIEs  NBAP-PROTOCOL-EXTENSION ::= {
	...
}

DL-DPCH-InformationModify-ModifyList-RL-ReconfPrepTDD ::= ProtocolIE-Single-Container {{ DL-DPCH-InformationModify-ModifyListIEs-RL-ReconfPrepTDD }}

DL-DPCH-InformationModify-ModifyListIEs-RL-ReconfPrepTDD NBAP-PROTOCOL-IES ::= {
	{ ID id-DL-DPCH-InformationModify-ModifyListIE-RL-ReconfPrepTDD   CRITICALITY reject		TYPE DL-DPCH-InformationModify-ModifyItem-RL-ReconfPrepTDD		PRESENCE mandatory }
}

DL-DPCH-InformationModify-ModifyItem-RL-ReconfPrepTDD ::= SEQUENCE {
	repetitionPeriod						RepetitionPeriod			OPTIONAL,
	repetitionLength						RepetitionLength			OPTIONAL,
	tdd-DPCHOffset							TDD-DPCHOffset				OPTIONAL,
	dL-Timeslot-InformationAddModify-ModifyList-RL-ReconfPrepTDD		DL-Timeslot-InformationModify-ModifyList-RL-ReconfPrepTDD			OPTIONAL,
	iE-Extensions								ProtocolExtensionContainer { { DL-DPCH-InformationModify-ModifyItem-RL-ReconfPrepTDD-ExtIEs} }		OPTIONAL,
	...
}

DL-DPCH-InformationModify-ModifyItem-RL-ReconfPrepTDD-ExtIEs  NBAP-PROTOCOL-EXTENSION ::= {
	{ ID id-DL-Timeslot-LCR-InformationModify-ModifyList-RL-ReconfPrepTDD   CRITICALITY reject			EXTENSION		 DL-Timeslot-LCR-InformationModify-ModifyList-RL-ReconfPrepTDD		PRESENCE optional },
	...
}

DL-Timeslot-InformationModify-ModifyList-RL-ReconfPrepTDD ::= SEQUENCE (SIZE (1..maxNrOfDLTSs)) OF DL-Timeslot-InformationModify-ModifyItem-RL-ReconfPrepTDD

DL-Timeslot-InformationModify-ModifyItem-RL-ReconfPrepTDD	 ::= SEQUENCE {
	timeSlot								TimeSlot,
	midambleShiftAndBurstType				MidambleShiftAndBurstType			OPTIONAL,
	tFCI-Presence							TFCI-Presence			OPTIONAL,
	dL-Code-InformationModify-ModifyList-RL-ReconfPrepTDD				DL-Code-InformationModify-ModifyList-RL-ReconfPrepTDD			OPTIONAL,
	iE-Extensions							ProtocolExtensionContainer { { DL-Timeslot-InformationModify-ModifyItem-RL-ReconfPrepTDD-ExtIEs} }		OPTIONAL,
	...
}

DL-Timeslot-InformationModify-ModifyItem-RL-ReconfPrepTDD-ExtIEs NBAP-PROTOCOL-EXTENSION ::= {
	...
}
DL-Code-InformationModify-ModifyList-RL-ReconfPrepTDD ::= SEQUENCE (SIZE (0..maxNrOfDPCHs)) OF DL-Code-InformationModify-ModifyItem-RL-ReconfPrepTDD

DL-Code-InformationModify-ModifyItem-RL-ReconfPrepTDD	 ::= SEQUENCE {
	dPCH-ID									DPCH-ID,
	tdd-ChannelisationCode					TDD-ChannelisationCode		OPTIONAL,
	iE-Extensions							ProtocolExtensionContainer { { DL-Code-InformationModify-ModifyItem-RL-ReconfPrepTDD-ExtIEs} }		OPTIONAL,
	...
}

DL-Code-InformationModify-ModifyItem-RL-ReconfPrepTDD-ExtIEs NBAP-PROTOCOL-EXTENSION ::= {
	...
}

DL-Timeslot-LCR-InformationModify-ModifyList-RL-ReconfPrepTDD ::= SEQUENCE (SIZE (1..maxNrOfDLTSLCRs)) OF DL-Timeslot-InformationModify-ModifyItem-RL-ReconfPrepTDD

DL-Timeslot-LCR-InformationModify-ModifyItem-RL-ReconfPrepTDD	 ::= SEQUENCE {
	timeSlotLCR								TimeSlotLCR,
	midambleShiftLCR			MidambleShiftLCR			OPTIONAL,
	tFCI-Presence							TFCI-Presence			OPTIONAL,
	dL-Code-LCR-InformationModify-ModifyList-RL-ReconfPrepTDD				DL-Code-LCR-InformationModify-ModifyList-RL-ReconfPrepTDD			OPTIONAL,
	iE-Extensions							ProtocolExtensionContainer { { DL-Timeslot-LCR-InformationModify-ModifyItem-RL-ReconfPrepTDD-ExtIEs} }		OPTIONAL,
	...
}

DL-Timeslot-LCR-InformationModify-ModifyItem-RL-ReconfPrepTDD-ExtIEs NBAP-PROTOCOL-EXTENSION ::= {
	...
}
DL-Code-LCR-InformationModify-ModifyList-RL-ReconfPrepTDD ::= SEQUENCE (SIZE (1..maxNrOfDPCHs)) OF DL-Code-InformationModify-ModifyItem-RL-ReconfPrepTDD

DL-Code-LCR-InformationModify-ModifyItem-RL-ReconfPrepTDD	 ::= SEQUENCE {
	dPCH-ID									DPCH-ID,
	tdd-ChannelisationCodeLCR				TDD-ChannelisationCodeLCR		OPTIONAL,
	iE-Extensions							ProtocolExtensionContainer { { DL-Code-LCR-InformationModify-ModifyItem-RL-ReconfPrepTDD-ExtIEs} }		OPTIONAL,
	...
}

DL-Code-LCR-InformationModify-ModifyItem-RL-ReconfPrepTDD-ExtIEs NBAP-PROTOCOL-EXTENSION ::= {
	{ ID id-DL-DPCH-TimeSlotFormat-LCR-ModifyItem-RL-ReconfPrepTDD	 CRITICALITY	reject	 EXTENSION TDD-DL-DPCH-TimeSlotFormat-LCR   PRESENCE  optional},
	...
}

DL-DPCH-InformationModify-DeleteList-RL-ReconfPrepTDD ::= ProtocolIE-Single-Container {{ DL-DPCH-InformationModify-DeleteListIEs-RL-ReconfPrepTDD }}

DL-DPCH-InformationModify-DeleteListIEs-RL-ReconfPrepTDD NBAP-PROTOCOL-IES ::= {
	{ ID id-DL-DPCH-InformationModify-DeleteListIE-RL-ReconfPrepTDD   CRITICALITY reject		TYPE DL-DPCH-InformationModify-DeleteListIE-RL-ReconfPrepTDD		PRESENCE mandatory }
}

DL-DPCH-InformationModify-DeleteListIE-RL-ReconfPrepTDD ::= SEQUENCE (SIZE (1..maxNrOfDPCHs)) OF DL-DPCH-InformationModify-DeleteItem-RL-ReconfPrepTDD

DL-DPCH-InformationModify-DeleteItem-RL-ReconfPrepTDD ::= SEQUENCE {
	dPCH-ID										DPCH-ID,
	iE-Extensions								ProtocolExtensionContainer { { DL-DPCH-InformationModify-DeleteItem-RL-ReconfPrepTDD-ExtIEs} }		OPTIONAL,
	...
}

DL-DPCH-InformationModify-DeleteItem-RL-ReconfPrepTDD-ExtIEs  NBAP-PROTOCOL-EXTENSION ::= {
	...
}

DL-CCTrCH-InformationDeleteList-RL-ReconfPrepTDD ::= SEQUENCE (SIZE (1..maxNrOfCCTrCHs)) OF DL-CCTrCH-InformationDeleteItem-RL-ReconfPrepTDD

DL-CCTrCH-InformationDeleteItem-RL-ReconfPrepTDD ::= SEQUENCE {
	cCTrCH-ID										CCTrCH-ID,
	iE-Extensions									ProtocolExtensionContainer { { DL-CCTrCH-InformationDeleteItem-RL-ReconfPrepTDD-ExtIEs} }			OPTIONAL,
	...
}

DL-CCTrCH-InformationDeleteItem-RL-ReconfPrepTDD-ExtIEs  NBAP-PROTOCOL-EXTENSION ::= {
	...
}

DCH-DeleteList-RL-ReconfPrepTDD ::= SEQUENCE (SIZE (1..maxNrOfDCHs)) OF DCH-DeleteItem-RL-ReconfPrepTDD

DCH-DeleteItem-RL-ReconfPrepTDD ::= SEQUENCE {
	dCH-ID										DCH-ID,
	iE-Extensions								ProtocolExtensionContainer { { DCH-DeleteItem-RL-ReconfPrepTDD-ExtIEs} }		OPTIONAL,
	...
}

DCH-DeleteItem-RL-ReconfPrepTDD-ExtIEs  NBAP-PROTOCOL-EXTENSION ::= {
	...
}

DSCH-Information-ModifyList-RL-ReconfPrepTDD ::= SEQUENCE (SIZE (1..maxNrOfDSCHs)) OF DSCH-Information-ModifyItem-RL-ReconfPrepTDD

DSCH-Information-ModifyItem-RL-ReconfPrepTDD ::= SEQUENCE {
 	dSCH-ID										DSCH-ID,
	cCTrCH-ID									CCTrCH-ID				OPTIONAL,
 	transportFormatSet							TransportFormatSet		OPTIONAL,
	allocationRetentionPriority					AllocationRetentionPriority	OPTIONAL,
	frameHandlingPriority						FrameHandlingPriority	OPTIONAL,
 	toAWS										ToAWS					OPTIONAL,
	toAWE										ToAWE					OPTIONAL,
	transportBearerRequestIndicator				TransportBearerRequestIndicator,
	iE-Extensions								ProtocolExtensionContainer { { DSCH-Information-ModifyItem-RL-ReconfPrepTDD-ExtIEs} }		OPTIONAL,
	...
 }

DSCH-Information-ModifyItem-RL-ReconfPrepTDD-ExtIEs  NBAP-PROTOCOL-EXTENSION ::= {
	{ ID id-bindingID						CRITICALITY	ignore		EXTENSION 	BindingID		PRESENCE 	optional	}|
	{ ID id-transportlayeraddress			CRITICALITY	ignore		EXTENSION 	TransportLayerAddress		PRESENCE 	optional	},
	...
}

DSCH-Information-DeleteList-RL-ReconfPrepTDD ::= SEQUENCE (SIZE (1..maxNrOfDSCHs)) OF DSCH-Information-DeleteItem-RL-ReconfPrepTDD

DSCH-Information-DeleteItem-RL-ReconfPrepTDD ::= SEQUENCE {
	dSCH-ID										DSCH-ID,
	iE-Extensions								ProtocolExtensionContainer { { DSCH-Information-DeleteItem-RL-ReconfPrepTDD-ExtIEs} }		OPTIONAL,
	...
}

DSCH-Information-DeleteItem-RL-ReconfPrepTDD-ExtIEs  NBAP-PROTOCOL-EXTENSION ::= {
	...
}

USCH-Information-ModifyList-RL-ReconfPrepTDD ::= SEQUENCE (SIZE (1..maxNrOfUSCHs)) OF USCH-Information-ModifyItem-RL-ReconfPrepTDD

USCH-Information-ModifyItem-RL-ReconfPrepTDD ::= SEQUENCE {
 	uSCH-ID										USCH-ID,
 	transportFormatSet							TransportFormatSet		OPTIONAL,
	allocationRetentionPriority					AllocationRetentionPriority	OPTIONAL,
	cCTrCH-ID									CCTrCH-ID				OPTIONAL,
	transportBearerRequestIndicator				TransportBearerRequestIndicator,
	iE-Extensions								ProtocolExtensionContainer { { USCH-Information-ModifyItem-RL-ReconfPrepTDD-ExtIEs} }		OPTIONAL,
	...
}

USCH-Information-ModifyItem-RL-ReconfPrepTDD-ExtIEs  NBAP-PROTOCOL-EXTENSION ::= {
	{ ID id-bindingID						CRITICALITY	ignore		EXTENSION 	BindingID		PRESENCE 	optional	}|
	{ ID id-transportlayeraddress			CRITICALITY	ignore		EXTENSION 	TransportLayerAddress		PRESENCE 	optional	},
	...
}

USCH-Information-DeleteList-RL-ReconfPrepTDD ::= SEQUENCE (SIZE (1..maxNrOfUSCHs)) OF USCH-Information-DeleteItem-RL-ReconfPrepTDD

USCH-Information-DeleteItem-RL-ReconfPrepTDD ::= SEQUENCE {
	uSCH-ID										USCH-ID,
	iE-Extensions								ProtocolExtensionContainer { { USCH-Information-DeleteItem-RL-ReconfPrepTDD-ExtIEs} }		OPTIONAL,
	...

}

USCH-Information-DeleteItem-RL-ReconfPrepTDD-ExtIEs  NBAP-PROTOCOL-EXTENSION ::= {
	...
}

RL-Information-RL-ReconfPrepTDD ::= SEQUENCE {
	rL-ID										RL-ID,
	maxDL-Power									DL-Power			OPTIONAL,
	minDL-Power									DL-Power			OPTIONAL,
	iE-Extensions								ProtocolExtensionContainer { { RL-Information-RL-ReconfPrepTDD-ExtIEs} }		OPTIONAL,
	...
}

RL-Information-RL-ReconfPrepTDD-ExtIEs  NBAP-PROTOCOL-EXTENSION ::= {
	{ ID id-InitDL-Power		CRITICALITY ignore		EXTENSION DL-Power		PRESENCE optional	}|
	{ ID id-RL-Specific-DCH-Info		CRITICALITY	ignore		EXTENSION 	RL-Specific-DCH-Info	PRESENCE 	optional	}|
	{ ID id-UL-Synchronisation-Parameters-LCR			CRITICALITY	ignore		EXTENSION 	UL-Synchronisation-Parameters-LCR		PRESENCE 	optional	},	-- Mandatory for 1.28Mcps TDD, Not Applicable to 3.84Mcps TDD
	...
}

HSDSCH-DeleteList-RL-ReconfPrepTDD ::= SEQUENCE (SIZE (1..maxNrOfMACdFlows)) OF HSDSCH-DeleteItem-RL-ReconfPrepTDD

HSDSCH-DeleteItem-RL-ReconfPrepTDD ::= SEQUENCE {
	hsDSCH-MACdFlow-ID								HSDSCH-MACdFlow-ID,
	iE-Extensions									ProtocolExtensionContainer { { HSDSCH-DeleteItem-RL-ReconfPrepTDD-ExtIEs} }		OPTIONAL,
	...
}

HSDSCH-DeleteItem-RL-ReconfPrepTDD-ExtIEs  NBAP-PROTOCOL-EXTENSION ::= {
	...
}

-- **************************************************************
--
-- RADIO LINK RECONFIGURATION READY
--
-- **************************************************************

RadioLinkReconfigurationReady ::= SEQUENCE {
	protocolIEs				ProtocolIE-Container	{{RadioLinkReconfigurationReady-IEs}},
	protocolExtensions		ProtocolExtensionContainer	{{RadioLinkReconfigurationReady-Extensions}}		OPTIONAL,
	...
}

RadioLinkReconfigurationReady-IEs NBAP-PROTOCOL-IES ::= {
	{ ID	id-CRNC-CommunicationContextID						CRITICALITY		ignore		TYPE	CRNC-CommunicationContextID						PRESENCE	mandatory	} |
	{ ID	id-RL-InformationResponseList-RL-ReconfReady		CRITICALITY		ignore		TYPE	RL-InformationResponseList-RL-ReconfReady		PRESENCE	optional	} |
	{ ID	id-CriticalityDiagnostics							CRITICALITY		ignore		TYPE	CriticalityDiagnostics							PRESENCE	optional	},
	...
}

RadioLinkReconfigurationReady-Extensions NBAP-PROTOCOL-EXTENSION ::= {
	{ ID id-TargetCommunicationControlPortID	CRITICALITY ignore	EXTENSION	CommunicationControlPortID				PRESENCE optional	},
	...
}

RL-InformationResponseList-RL-ReconfReady	 ::= SEQUENCE (SIZE (1..maxNrOfRLs)) OF ProtocolIE-Single-Container {{ RL-InformationResponseItemIE-RL-ReconfReady}}

RL-InformationResponseItemIE-RL-ReconfReady NBAP-PROTOCOL-IES ::= {
	{ ID	id-RL-InformationResponseItem-RL-ReconfReady			CRITICALITY		ignore			TYPE	RL-InformationResponseItem-RL-ReconfReady		PRESENCE	mandatory}
}

RL-InformationResponseItem-RL-ReconfReady ::= SEQUENCE {
	rL-ID											RL-ID,
	dCH-InformationResponseList-RL-ReconfReady		DCH-InformationResponseList-RL-ReconfReady	OPTIONAL,
	dSCH-InformationResponseList-RL-ReconfReady		DSCH-InformationResponseList-RL-ReconfReady	OPTIONAL,
	uSCH-InformationResponseList-RL-ReconfReady		USCH-InformationResponseList-RL-ReconfReady	OPTIONAL, -- TDD only
	tFCI2-BearerInformationResponse					TFCI2-BearerInformationResponse 	OPTIONAL,
	-- FDD only. There shall be only one TFCI2 bearer per Node B Communication Context.
	iE-Extensions									ProtocolExtensionContainer { { RL-InformationResponseItem-RL-ReconfReady-ExtIEs} }		OPTIONAL,
	...
}

RL-InformationResponseItem-RL-ReconfReady-ExtIEs  NBAP-PROTOCOL-EXTENSION ::= {
	{ ID id-DL-PowerBalancing-UpdatedIndicator	CRITICALITY ignore		EXTENSION		DL-PowerBalancing-UpdatedIndicator		PRESENCE optional}|
	{ ID id-HSDSCH-FDD-Information-Response			CRITICALITY ignore		EXTENSION HSDSCH-FDD-Information-Response		PRESENCE optional	}|
	{ ID id-HSDSCH-TDD-Information-Response			CRITICALITY ignore		EXTENSION HSDSCH-TDD-Information-Response		PRESENCE optional	},
	...
}

DCH-InformationResponseList-RL-ReconfReady::= ProtocolIE-Single-Container {{ DCH-InformationResponseListIEs-RL-ReconfReady }}

DCH-InformationResponseListIEs-RL-ReconfReady NBAP-PROTOCOL-IES ::= {
	{ ID id-DCH-InformationResponse   CRITICALITY ignore	TYPE DCH-InformationResponse	PRESENCE mandatory }
}

DSCH-InformationResponseList-RL-ReconfReady::= ProtocolIE-Single-Container {{ DSCH-InformationResponseListIEs-RL-ReconfReady }}

DSCH-InformationResponseListIEs-RL-ReconfReady NBAP-PROTOCOL-IES ::= {
	{ ID id-DSCH-InformationResponse   CRITICALITY ignore	TYPE DSCH-InformationResponse	PRESENCE mandatory }
}

USCH-InformationResponseList-RL-ReconfReady::= ProtocolIE-Single-Container {{ USCH-InformationResponseListIEs-RL-ReconfReady }}

USCH-InformationResponseListIEs-RL-ReconfReady NBAP-PROTOCOL-IES ::= {
	{ ID id-USCH-InformationResponse   CRITICALITY ignore	TYPE USCH-InformationResponse		PRESENCE mandatory }
}

-- **************************************************************
--
-- RADIO LINK RECONFIGURATION FAILURE
--
-- **************************************************************

RadioLinkReconfigurationFailure ::= SEQUENCE {
	protocolIEs				ProtocolIE-Container	{{RadioLinkReconfigurationFailure-IEs}},
	protocolExtensions		ProtocolExtensionContainer	{{RadioLinkReconfigurationFailure-Extensions}}		OPTIONAL,
	...
}

RadioLinkReconfigurationFailure-IEs NBAP-PROTOCOL-IES ::= {
	{ ID	id-CRNC-CommunicationContextID						CRITICALITY		ignore		TYPE	CRNC-CommunicationContextID							PRESENCE	mandatory	} |
	{ ID	id-CauseLevel-RL-ReconfFailure	CRITICALITY		ignore		TYPE	CauseLevel-RL-ReconfFailure		PRESENCE	mandatory	} |
	{ ID	id-CriticalityDiagnostics							CRITICALITY		ignore		TYPE	CriticalityDiagnostics								PRESENCE	optional	},
	...
}

RadioLinkReconfigurationFailure-Extensions NBAP-PROTOCOL-EXTENSION ::= {
	...
}

CauseLevel-RL-ReconfFailure ::= CHOICE {
	generalCause		GeneralCauseList-RL-ReconfFailure,
	rLSpecificCause		RLSpecificCauseList-RL-ReconfFailure,
	...
}

GeneralCauseList-RL-ReconfFailure ::= SEQUENCE {
	cause										Cause,
	iE-Extensions								ProtocolExtensionContainer { { GeneralCauseItem-RL-ReconfFailure-ExtIEs} }			OPTIONAL,
	...
 }

GeneralCauseItem-RL-ReconfFailure-ExtIEs  NBAP-PROTOCOL-EXTENSION ::= {
	...
}

RLSpecificCauseList-RL-ReconfFailure ::= SEQUENCE {
	rL-ReconfigurationFailureList-RL-ReconfFailure		RL-ReconfigurationFailureList-RL-ReconfFailure		OPTIONAL,
	iE-Extensions										ProtocolExtensionContainer { { RLSpecificCauseItem-RL-ReconfFailure-ExtIEs} }			OPTIONAL,
	...
 }

RLSpecificCauseItem-RL-ReconfFailure-ExtIEs  NBAP-PROTOCOL-EXTENSION ::= {
	...
}

RL-ReconfigurationFailureList-RL-ReconfFailure ::= SEQUENCE (SIZE (1..maxNrOfRLs)) OF ProtocolIE-Single-Container {{ RL-ReconfigurationFailureItemIE-RL-ReconfFailure}}

RL-ReconfigurationFailureItemIE-RL-ReconfFailure NBAP-PROTOCOL-IES ::= {
	{ ID	id-RL-ReconfigurationFailureItem-RL-ReconfFailure			CRITICALITY		ignore		TYPE 	RL-ReconfigurationFailureItem-RL-ReconfFailure			PRESENCE	mandatory}
}

RL-ReconfigurationFailureItem-RL-ReconfFailure ::= SEQUENCE {
 	rL-ID										RL-ID,
	cause										Cause,
	iE-Extensions								ProtocolExtensionContainer { { RL-ReconfigurationFailureItem-RL-ReconfFailure-ExtIEs} }			OPTIONAL,
	...
 }

RL-ReconfigurationFailureItem-RL-ReconfFailure-ExtIEs  NBAP-PROTOCOL-EXTENSION ::= {
	...
}

-- **************************************************************
--
-- RADIO LINK RECONFIGURATION COMMIT
--
-- **************************************************************

RadioLinkReconfigurationCommit ::= SEQUENCE {
	protocolIEs				ProtocolIE-Container	{{RadioLinkReconfigurationCommit-IEs}},
	protocolExtensions		ProtocolExtensionContainer	{{RadioLinkReconfigurationCommit-Extensions}}		OPTIONAL,
	...
}

RadioLinkReconfigurationCommit-IEs NBAP-PROTOCOL-IES ::= {
	{ ID	id-NodeB-CommunicationContextID			CRITICALITY		ignore		TYPE	NodeB-CommunicationContextID		PRESENCE	mandatory	} |
	{ ID	id-CFN									CRITICALITY		ignore		TYPE	CFN									PRESENCE	mandatory	}|
	{ ID 	id-Active-Pattern-Sequence-Information	CRITICALITY 	ignore		TYPE 	Active-Pattern-Sequence-Information	 PRESENCE optional },
	...
}

RadioLinkReconfigurationCommit-Extensions NBAP-PROTOCOL-EXTENSION ::= {
	...
}

-- **************************************************************
--
-- RADIO LINK RECONFIGURATION CANCEL
--
-- **************************************************************

RadioLinkReconfigurationCancel ::= SEQUENCE {
	protocolIEs				ProtocolIE-Container	{{RadioLinkReconfigurationCancel-IEs}},
	protocolExtensions		ProtocolExtensionContainer	{{RadioLinkReconfigurationCancel-Extensions}}		OPTIONAL,
	...
}

RadioLinkReconfigurationCancel-IEs NBAP-PROTOCOL-IES ::= {
	{ ID	id-NodeB-CommunicationContextID			CRITICALITY 	ignore		TYPE	NodeB-CommunicationContextID			PRESENCE	mandatory	},
	...
}

RadioLinkReconfigurationCancel-Extensions NBAP-PROTOCOL-EXTENSION ::= {
	...
}

-- **************************************************************
--
-- RADIO LINK RECONFIGURATION REQUEST FDD
--
-- **************************************************************

RadioLinkReconfigurationRequestFDD ::= SEQUENCE {
	protocolIEs				ProtocolIE-Container	{{RadioLinkReconfigurationRequestFDD-IEs}},
	protocolExtensions		ProtocolExtensionContainer	{{RadioLinkReconfigurationRequestFDD-Extensions}}		OPTIONAL,
	...
}

RadioLinkReconfigurationRequestFDD-IEs NBAP-PROTOCOL-IES ::= {
	{ ID	id-NodeB-CommunicationContextID					CRITICALITY		reject		TYPE	NodeB-CommunicationContextID				PRESENCE	mandatory	} |
	{ ID	id-UL-DPCH-Information-RL-ReconfRqstFDD			CRITICALITY		reject		TYPE	UL-DPCH-Information-RL-ReconfRqstFDD			PRESENCE	optional	} |
	{ ID	id-DL-DPCH-Information-RL-ReconfRqstFDD			CRITICALITY		reject		TYPE	DL-DPCH-Information-RL-ReconfRqstFDD			PRESENCE	optional	} |
	{ ID	id-FDD-DCHs-to-Modify				CRITICALITY		reject		TYPE	FDD-DCHs-to-Modify				PRESENCE	optional	} |
	{ ID	id-DCHs-to-Add-FDD					CRITICALITY		reject		TYPE	DCH-FDD-Information					PRESENCE	optional	} |
	{ ID	id-DCH-DeleteList-RL-ReconfRqstFDD				CRITICALITY		reject		TYPE	DCH-DeleteList-RL-ReconfRqstFDD				PRESENCE	optional	} |
	{ ID	id-RL-InformationList-RL-ReconfRqstFDD			CRITICALITY		reject		TYPE	RL-InformationList-RL-ReconfRqstFDD			PRESENCE	optional	}|
	{ ID id-Transmission-Gap-Pattern-Sequence-Information	CRITICALITY 	reject		TYPE 	Transmission-Gap-Pattern-Sequence-Information	 PRESENCE optional },
	...
}

RadioLinkReconfigurationRequestFDD-Extensions NBAP-PROTOCOL-EXTENSION ::= {
	{ ID id-SignallingBearerRequestIndicator	CRITICALITY reject	EXTENSION	SignallingBearerRequestIndicator					PRESENCE optional	},
	...
}


UL-DPCH-Information-RL-ReconfRqstFDD ::= SEQUENCE {
	ul-TFCS											TFCS			OPTIONAL,
	iE-Extensions									ProtocolExtensionContainer { { UL-DPCH-Information-RL-ReconfRqstFDD-ExtIEs} }		OPTIONAL,
	...
}

UL-DPCH-Information-RL-ReconfRqstFDD-ExtIEs NBAP-PROTOCOL-EXTENSION ::= {
	...
}

DL-DPCH-Information-RL-ReconfRqstFDD ::= SEQUENCE {
	dl-TFCS											TFCS			OPTIONAL,
 	tFCI-SignallingMode								TFCI-SignallingMode						OPTIONAL,
	limitedPowerIncrease							LimitedPowerIncrease					OPTIONAL,
	iE-Extensions									ProtocolExtensionContainer { { DL-DPCH-Information-RL-ReconfRqstFDD-ExtIEs} }		OPTIONAL,
	...
 }

DL-DPCH-Information-RL-ReconfRqstFDD-ExtIEs NBAP-PROTOCOL-EXTENSION ::= {
	...
}

DCH-DeleteList-RL-ReconfRqstFDD ::= SEQUENCE (SIZE (1..maxNrOfDCHs)) OF DCH-DeleteItem-RL-ReconfRqstFDD

DCH-DeleteItem-RL-ReconfRqstFDD ::= SEQUENCE {
	dCH-ID											DCH-ID,
	iE-Extensions									ProtocolExtensionContainer { { DCH-DeleteItem-RL-ReconfRqstFDD-ExtIEs} }			OPTIONAL,
	...

}

DCH-DeleteItem-RL-ReconfRqstFDD-ExtIEs  NBAP-PROTOCOL-EXTENSION ::= {
	...
}

RL-InformationList-RL-ReconfRqstFDD ::= SEQUENCE (SIZE (1..maxNrOfRLs)) OF ProtocolIE-Single-Container {{ RL-InformationItemIE-RL-ReconfRqstFDD}}

RL-InformationItemIE-RL-ReconfRqstFDD NBAP-PROTOCOL-IES ::= {
	{ ID	id-RL-InformationItem-RL-ReconfRqstFDD				CRITICALITY		reject			TYPE	RL-InformationItem-RL-ReconfRqstFDD			PRESENCE	mandatory}
}

RL-InformationItem-RL-ReconfRqstFDD ::= SEQUENCE {
	rL-ID										RL-ID,
	maxDL-Power									DL-Power		OPTIONAL,
	minDL-Power									DL-Power		OPTIONAL,
	dl-CodeInformation						FDD-DL-CodeInformation		OPTIONAL,
-- The IE shall be present if the Transmission Gap Pattern Sequence Information IE is included and the indicated Downlink Compressed Mode method for at least one of the included Transmission Gap Pattern Sequence is set to "SF/2".
	iE-Extensions								ProtocolExtensionContainer { { RL-InformationItem-RL-ReconfRqstFDD-ExtIEs} }			OPTIONAL,
	...
}

RL-InformationItem-RL-ReconfRqstFDD-ExtIEs  NBAP-PROTOCOL-EXTENSION ::= {
	{ ID id-DLReferencePower			CRITICALITY ignore	EXTENSION	DL-Power				PRESENCE optional	}|
	{ ID id-RL-Specific-DCH-Info		CRITICALITY	ignore		EXTENSION 	RL-Specific-DCH-Info	PRESENCE 	optional	},
	...
}

-- **************************************************************
--
-- RADIO LINK RECONFIGURATION REQUEST TDD
--
-- **************************************************************

RadioLinkReconfigurationRequestTDD ::= SEQUENCE {
	protocolIEs				ProtocolIE-Container	{{RadioLinkReconfigurationRequestTDD-IEs}},
	protocolExtensions		ProtocolExtensionContainer	{{RadioLinkReconfigurationRequestTDD-Extensions}}		OPTIONAL,
	...
}

RadioLinkReconfigurationRequestTDD-IEs NBAP-PROTOCOL-IES ::= {
	{ ID	id-NodeB-CommunicationContextID							CRITICALITY		reject			TYPE	NodeB-CommunicationContextID					PRESENCE	mandatory	} |
	{ ID	id-UL-CCTrCH-InformationModifyList-RL-ReconfRqstTDD			CRITICALITY		notify			TYPE 	UL-CCTrCH-InformationModifyList-RL-ReconfRqstTDD		PRESENCE	optional	} |
	{ ID	id-UL-CCTrCH-InformationDeleteList-RL-ReconfRqstTDD			CRITICALITY		notify			TYPE 	UL-CCTrCH-InformationDeleteList-RL-ReconfRqstTDD		PRESENCE	optional	} |
	{ ID 	id-DL-CCTrCH-InformationModifyList-RL-ReconfRqstTDD			CRITICALITY		notify			TYPE	DL-CCTrCH-InformationModifyList-RL-ReconfRqstTDD		PRESENCE 	optional	} |
	{ ID 	id-DL-CCTrCH-InformationDeleteList-RL-ReconfRqstTDD			CRITICALITY		notify			TYPE	DL-CCTrCH-InformationDeleteList-RL-ReconfRqstTDD		PRESENCE 	optional	} |
	{ ID	id-TDD-DCHs-to-Modify						CRITICALITY		reject			TYPE	TDD-DCHs-to-Modify					PRESENCE	optional	} |
		{ ID	id-DCHs-to-Add-TDD							CRITICALITY		reject			TYPE 	DCH-TDD-Information					PRESENCE 	optional	} |
	{ ID	id-DCH-DeleteList-RL-ReconfRqstTDD						CRITICALITY		reject			TYPE 	DCH-DeleteList-RL-ReconfRqstTDD					PRESENCE	optional	} |
	{ ID	id-RL-Information-RL-ReconfRqstTDD					CRITICALITY		reject			TYPE	RL-Information-RL-ReconfRqstTDD				PRESENCE	optional	},
	...
}

RadioLinkReconfigurationRequestTDD-Extensions NBAP-PROTOCOL-EXTENSION ::= {
	{ ID id-SignallingBearerRequestIndicator	CRITICALITY reject	EXTENSION	SignallingBearerRequestIndicator					PRESENCE optional	},
	...
}

UL-CCTrCH-InformationModifyList-RL-ReconfRqstTDD ::= SEQUENCE (SIZE (1..maxNrOfCCTrCHs)) OF ProtocolIE-Single-Container {{ UL-CCTrCH-InformationModifyItemIE-RL-ReconfRqstTDD}}

UL-CCTrCH-InformationModifyItemIE-RL-ReconfRqstTDD NBAP-PROTOCOL-IES ::= {
	{ ID	id-UL-CCTrCH-InformationModifyItem-RL-ReconfRqstTDD			CRITICALITY		notify			TYPE 	UL-CCTrCH-InformationModifyItem-RL-ReconfRqstTDD		PRESENCE	mandatory}
}

UL-CCTrCH-InformationModifyItem-RL-ReconfRqstTDD ::= SEQUENCE {
	cCTrCH-ID										CCTrCH-ID,
	tFCS											TFCS			OPTIONAL,
	punctureLimit									PunctureLimit	OPTIONAL,
	iE-Extensions									ProtocolExtensionContainer { { UL-CCTrCH-InformationModifyItem-RL-ReconfRqstTDD-ExtIEs} }			OPTIONAL,
	...
}

UL-CCTrCH-InformationModifyItem-RL-ReconfRqstTDD-ExtIEs  NBAP-PROTOCOL-EXTENSION ::= {
{ ID id-UL-SIRTarget        CRITICALITY reject      EXTENSION       UL-SIR      PRESENCE	optional   },
    -- Applicable to 1.28Mcps TDD only
	...
}

UL-CCTrCH-InformationDeleteList-RL-ReconfRqstTDD ::= SEQUENCE (SIZE (1..maxNrOfCCTrCHs)) OF ProtocolIE-Single-Container {{ UL-CCTrCH-InformationDeleteItemIE-RL-ReconfRqstTDD}}

UL-CCTrCH-InformationDeleteItemIE-RL-ReconfRqstTDD NBAP-PROTOCOL-IES ::= {
	{ ID	id-UL-CCTrCH-InformationDeleteItem-RL-ReconfRqstTDD			CRITICALITY		notify			TYPE 	UL-CCTrCH-InformationDeleteItem-RL-ReconfRqstTDD		PRESENCE	mandatory}
}

UL-CCTrCH-InformationDeleteItem-RL-ReconfRqstTDD ::= SEQUENCE {
	cCTrCH-ID										CCTrCH-ID,
	iE-Extensions									ProtocolExtensionContainer { { UL-CCTrCH-InformationDeleteItem-RL-ReconfRqstTDD-ExtIEs} }			OPTIONAL,
	...
}

UL-CCTrCH-InformationDeleteItem-RL-ReconfRqstTDD-ExtIEs  NBAP-PROTOCOL-EXTENSION ::= {
	...
}

DL-CCTrCH-InformationModifyList-RL-ReconfRqstTDD ::= SEQUENCE (SIZE (1..maxNrOfCCTrCHs)) OF ProtocolIE-Single-Container {{ DL-CCTrCH-InformationModifyItemIE-RL-ReconfRqstTDD}}

DL-CCTrCH-InformationModifyItemIE-RL-ReconfRqstTDD NBAP-PROTOCOL-IES ::= {
	{ ID	id-DL-CCTrCH-InformationModifyItem-RL-ReconfRqstTDD			CRITICALITY		notify			TYPE 	DL-CCTrCH-InformationModifyItem-RL-ReconfRqstTDD		PRESENCE	mandatory}
}

DL-CCTrCH-InformationModifyItem-RL-ReconfRqstTDD ::= SEQUENCE {
	cCTrCH-ID										CCTrCH-ID,
	tFCS											TFCS			OPTIONAL,
	punctureLimit									PunctureLimit	OPTIONAL,
	iE-Extensions									ProtocolExtensionContainer { { DL-CCTrCH-InformationModifyItem-RL-ReconfRqstTDD-ExtIEs} }			OPTIONAL,
	...
}

DL-CCTrCH-InformationModifyItem-RL-ReconfRqstTDD-ExtIEs  NBAP-PROTOCOL-EXTENSION ::= {
	...
}

DL-CCTrCH-InformationDeleteList-RL-ReconfRqstTDD ::= SEQUENCE (SIZE (1..maxNrOfCCTrCHs)) OF ProtocolIE-Single-Container {{ DL-CCTrCH-InformationDeleteItemIE-RL-ReconfRqstTDD}}

DL-CCTrCH-InformationDeleteItemIE-RL-ReconfRqstTDD NBAP-PROTOCOL-IES ::= {
	{ ID	id-DL-CCTrCH-InformationDeleteItem-RL-ReconfRqstTDD			CRITICALITY		notify			TYPE 	DL-CCTrCH-InformationDeleteItem-RL-ReconfRqstTDD		PRESENCE	mandatory}
}

DL-CCTrCH-InformationDeleteItem-RL-ReconfRqstTDD ::= SEQUENCE {
	cCTrCH-ID										CCTrCH-ID,
	iE-Extensions									ProtocolExtensionContainer { { DL-CCTrCH-InformationDeleteItem-RL-ReconfRqstTDD-ExtIEs} }			OPTIONAL,
	...
}

DL-CCTrCH-InformationDeleteItem-RL-ReconfRqstTDD-ExtIEs  NBAP-PROTOCOL-EXTENSION ::= {
	...
}

DCH-DeleteList-RL-ReconfRqstTDD ::= SEQUENCE (SIZE (1..maxNrOfDCHs)) OF DCH-DeleteItem-RL-ReconfRqstTDD

DCH-DeleteItem-RL-ReconfRqstTDD ::= SEQUENCE {
	dCH-ID											DCH-ID,
	iE-Extensions									ProtocolExtensionContainer { { DCH-DeleteItem-RL-ReconfRqstTDD-ExtIEs} }			OPTIONAL,
	...
}

DCH-DeleteItem-RL-ReconfRqstTDD-ExtIEs  NBAP-PROTOCOL-EXTENSION ::= {
	...
}

RL-Information-RL-ReconfRqstTDD ::= SEQUENCE {
	rL-ID										RL-ID,
	maxDL-Power									DL-Power		OPTIONAL,
	minDL-Power									DL-Power		OPTIONAL,
	iE-Extensions								ProtocolExtensionContainer { { RL-InformationItem-RL-ReconfRqstTDD-ExtIEs} }			OPTIONAL,
	...
}

RL-InformationItem-RL-ReconfRqstTDD-ExtIEs  NBAP-PROTOCOL-EXTENSION ::= {
	{ ID id-RL-Specific-DCH-Info		CRITICALITY	ignore		EXTENSION 	RL-Specific-DCH-Info	PRESENCE 	optional	}|
	{ ID id-UL-Synchronisation-Parameters-LCR			CRITICALITY	ignore		EXTENSION 	UL-Synchronisation-Parameters-LCR		PRESENCE 	optional	},	-- Mandatory for 1.28Mcps TDD, Not Applicable to 3.84Mcps TDD
	...
}

-- **************************************************************
--
-- RADIO LINK RECONFIGURATION RESPONSE
--
-- **************************************************************

RadioLinkReconfigurationResponse ::= SEQUENCE {
	protocolIEs				ProtocolIE-Container	{{RadioLinkReconfigurationResponse-IEs}},
	protocolExtensions		ProtocolExtensionContainer	{{RadioLinkReconfigurationResponse-Extensions}}		OPTIONAL,
	...
}

RadioLinkReconfigurationResponse-IEs NBAP-PROTOCOL-IES ::= {
	{ ID	id-CRNC-CommunicationContextID					CRITICALITY	ignore		TYPE	CRNC-CommunicationContextID						PRESENCE	mandatory	} |
	{ ID	id-RL-InformationResponseList-RL-ReconfRsp		CRITICALITY	ignore		TYPE	RL-InformationResponseList-RL-ReconfRsp			PRESENCE	optional	} |
	{ ID	id-CriticalityDiagnostics						CRITICALITY	ignore		TYPE	CriticalityDiagnostics							PRESENCE	optional	},
	...
}

RadioLinkReconfigurationResponse-Extensions NBAP-PROTOCOL-EXTENSION ::= {
	{ ID id-TargetCommunicationControlPortID	CRITICALITY ignore	EXTENSION	CommunicationControlPortID				PRESENCE optional	},
	...
}

RL-InformationResponseList-RL-ReconfRsp ::= SEQUENCE (SIZE (1..maxNrOfRLs)) OF ProtocolIE-Single-Container {{RL-InformationResponseItemIE-RL-ReconfRsp}}

RL-InformationResponseItemIE-RL-ReconfRsp NBAP-PROTOCOL-IES ::= {
	{ ID	id-RL-InformationResponseItem-RL-ReconfRsp			CRITICALITY		ignore			TYPE	RL-InformationResponseItem-RL-ReconfRsp			PRESENCE	mandatory}
}

RL-InformationResponseItem-RL-ReconfRsp ::= SEQUENCE {
	rL-ID										RL-ID,
	dCH-InformationResponseList-RL-ReconfRsp		DCH-InformationResponseList-RL-ReconfRsp		OPTIONAL,
	iE-Extensions								ProtocolExtensionContainer { { RL-InformationResponseItem-RL-ReconfRsp-ExtIEs} }		OPTIONAL,
	...
}

RL-InformationResponseItem-RL-ReconfRsp-ExtIEs  NBAP-PROTOCOL-EXTENSION ::= {
	{ ID id-DL-PowerBalancing-UpdatedIndicator	CRITICALITY ignore		EXTENSION		DL-PowerBalancing-UpdatedIndicator		PRESENCE optional},
	...
}

DCH-InformationResponseList-RL-ReconfRsp::= ProtocolIE-Single-Container {{ DCH-InformationResponseListIEs-RL-ReconfRsp }}

DCH-InformationResponseListIEs-RL-ReconfRsp NBAP-PROTOCOL-IES ::= {
	{ ID id-DCH-InformationResponse   CRITICALITY ignore	TYPE DCH-InformationResponse	PRESENCE mandatory }
}

-- **************************************************************
--
-- RADIO LINK DELETION REQUEST
--
-- **************************************************************

RadioLinkDeletionRequest ::= SEQUENCE {
	protocolIEs				ProtocolIE-Container	{{RadioLinkDeletionRequest-IEs}},
	protocolExtensions		ProtocolExtensionContainer	{{RadioLinkDeletionRequest-Extensions}}		OPTIONAL,
	...
}

RadioLinkDeletionRequest-IEs NBAP-PROTOCOL-IES ::= {
	{ ID	id-NodeB-CommunicationContextID					CRITICALITY		reject			TYPE	NodeB-CommunicationContextID				PRESENCE	mandatory		} |
	{ ID	id-CRNC-CommunicationContextID					CRITICALITY		reject				TYPE	CRNC-CommunicationContextID				PRESENCE	mandatory	}|
	{ ID	id-RL-informationList-RL-DeletionRqst			CRITICALITY		notify			TYPE	RL-informationList-RL-DeletionRqst			PRESENCE	mandatory		} ,
	...
}

RadioLinkDeletionRequest-Extensions NBAP-PROTOCOL-EXTENSION ::= {
	...
}

RL-informationList-RL-DeletionRqst ::= SEQUENCE (SIZE (1..maxNrOfRLs)) OF ProtocolIE-Single-Container {{RL-informationItemIE-RL-DeletionRqst}}

RL-informationItemIE-RL-DeletionRqst NBAP-PROTOCOL-IES ::= {
	{ ID	id-RL-informationItem-RL-DeletionRqst			CRITICALITY		notify			TYPE	RL-informationItem-RL-DeletionRqst				PRESENCE	mandatory}
}

RL-informationItem-RL-DeletionRqst ::= SEQUENCE {
 	rL-ID										RL-ID,
	iE-Extensions								ProtocolExtensionContainer { { RL-informationItem-RL-DeletionRqst-ExtIEs} }		OPTIONAL,
	...		
 }

RL-informationItem-RL-DeletionRqst-ExtIEs  NBAP-PROTOCOL-EXTENSION ::= {
	...
}

-- **************************************************************
--
-- RADIO LINK DELETION RESPONSE
--
-- **************************************************************

RadioLinkDeletionResponse ::= SEQUENCE {
	protocolIEs				ProtocolIE-Container	{{RadioLinkDeletionResponse-IEs}},
	protocolExtensions		ProtocolExtensionContainer	{{RadioLinkDeletionResponse-Extensions}}		OPTIONAL,
	...
}

RadioLinkDeletionResponse-IEs NBAP-PROTOCOL-IES ::= {
	{ ID	id-CRNC-CommunicationContextID			CRITICALITY		ignore			TYPE	CRNC-CommunicationContextID				PRESENCE	mandatory	}|
	{ ID	id-CriticalityDiagnostics				CRITICALITY		ignore			TYPE	CriticalityDiagnostics					PRESENCE	optional	},
	...
}

RadioLinkDeletionResponse-Extensions NBAP-PROTOCOL-EXTENSION ::= {
	...
}


-- **************************************************************
--
-- DL POWER CONTROL REQUEST FDD
--
-- **************************************************************

DL-PowerControlRequest ::= SEQUENCE {
	protocolIEs				ProtocolIE-Container	{{DL-PowerControlRequest-IEs}},
	protocolExtensions		ProtocolExtensionContainer	{{DL-PowerControlRequest-Extensions}}		OPTIONAL,
	...
}

DL-PowerControlRequest-IEs NBAP-PROTOCOL-IES ::= {
	{ ID id-NodeB-CommunicationContextID		CRITICALITY	ignore			TYPE	NodeB-CommunicationContextID				PRESENCE	mandatory	} |
	{ ID id-PowerAdjustmentType					CRITICALITY ignore	TYPE PowerAdjustmentType				PRESENCE mandatory} |
	{ ID id-DLReferencePower					CRITICALITY ignore	TYPE DL-Power							PRESENCE conditional} |
	-- This IE shall be present if the Adjustment Type IE is set to 'Common'
	{ ID id-InnerLoopDLPCStatus					CRITICALITY	ignore	TYPE InnerLoopDLPCStatus				PRESENCE	optional } |
	{ ID id-DLReferencePowerList-DL-PC-Rqst		CRITICALITY ignore	TYPE DL-ReferencePowerInformationList-DL-PC-Rqst	PRESENCE conditional } |
	-- This IE shall be present if the Adjustment Type IE is set to 'Individual'
	{ ID id-MaxAdjustmentStep					CRITICALITY ignore	TYPE MaxAdjustmentStep			PRESENCE conditional} |
	-- This IE shall be present if the Adjustment Type IE is set to 'Common' or 'Individual'
	{ ID id-AdjustmentPeriod					CRITICALITY ignore	TYPE AdjustmentPeriod			PRESENCE conditional }|
	-- This IE shall be present if the Adjustment Type IE is set to 'Common' or 'Individual'
	{ ID id-AdjustmentRatio			CRITICALITY ignore	TYPE ScaledAdjustmentRatio			PRESENCE conditional	},
	-- This IE shall be present if the Adjustment Type IE is set to 'Common' or 'Individual'
	...
}

DL-PowerControlRequest-Extensions NBAP-PROTOCOL-EXTENSION ::= {
	...
}

DL-ReferencePowerInformationList-DL-PC-Rqst ::= SEQUENCE (SIZE (1..maxNrOfRLs)) OF ProtocolIE-Single-Container {{DL-ReferencePowerInformationItemIE-DL-PC-Rqst }}

DL-ReferencePowerInformationItemIE-DL-PC-Rqst NBAP-PROTOCOL-IES ::= {
	{ ID id-DL-ReferencePowerInformationItem-DL-PC-Rqst		CRITICALITY		 ignore		TYPE 	DL-ReferencePowerInformationItem-DL-PC-Rqst		PRESENCE 	mandatory
}
}

DL-ReferencePowerInformationItem-DL-PC-Rqst ::= SEQUENCE {
	rL-ID									RL-ID,
	dl-ReferencePower						DL-Power,
	iE-Extensions							ProtocolExtensionContainer { { DL-ReferencePowerInformationItem-DL-PC-Rqst-ExtIEs } }		OPTIONAL,
	...		
}

DL-ReferencePowerInformationItem-DL-PC-Rqst-ExtIEs  NBAP-PROTOCOL-EXTENSION ::= {
	...
}

-- **************************************************************
--
-- DL POWER TIMESLOT CONTROL REQUEST TDD
--
-- **************************************************************

DL-PowerTimeslotControlRequest ::= SEQUENCE {
	protocolIEs				ProtocolIE-Container	{{DL-PowerTimeslotControlRequest-IEs}},
	protocolExtensions		ProtocolExtensionContainer	{{DL-PowerTimeslotControlRequest-Extensions}}		OPTIONAL,
	...
}

DL-PowerTimeslotControlRequest-IEs NBAP-PROTOCOL-IES ::= {
	{ ID id-NodeB-CommunicationContextID			CRITICALITY	ignore			TYPE	NodeB-CommunicationContextID				PRESENCE	mandatory	} |
	{ ID id-TimeslotISCPInfo		CRITICALITY	ignore			TYPE	DL-TimeslotISCPInfo		PRESENCE optional },
	-- Mandatory for 3.84Mcps TDD, Not Applicable to 1.28Mcps TDD

	...
}

DL-PowerTimeslotControlRequest-Extensions NBAP-PROTOCOL-EXTENSION ::= {
	{ ID id-TimeslotISCPInfoList-LCR-DL-PC-RqstTDD		CRITICALITY	ignore			EXTENSION	DL-TimeslotISCPInfoLCR		PRESENCE optional }|
	-- Mandatory for 1.28Mcps TDD, Not Applicable to 3.84Mcps TDD
	{ ID id-PrimCCPCH-RSCP-DL-PC-RqstTDD				CRITICALITY ignore			EXTENSION PrimaryCCPCH-RSCP		PRESENCE optional	},
	...
}

-- **************************************************************
--
-- DEDICATED MEASUREMENT INITIATION REQUEST
--
-- **************************************************************

DedicatedMeasurementInitiationRequest ::= SEQUENCE {
	protocolIEs				ProtocolIE-Container	{{DedicatedMeasurementInitiationRequest-IEs}},
	protocolExtensions		ProtocolExtensionContainer	{{DedicatedMeasurementInitiationRequest-Extensions}}		OPTIONAL,
	...
}

DedicatedMeasurementInitiationRequest-IEs NBAP-PROTOCOL-IES ::= {
	{ ID	id-NodeB-CommunicationContextID					CRITICALITY		reject		TYPE	NodeB-CommunicationContextID				PRESENCE	mandatory	} |
	{ ID	id-MeasurementID								CRITICALITY		reject		TYPE	MeasurementID								PRESENCE	mandatory	} |
	{ ID	id-DedicatedMeasurementObjectType-DM-Rqst		CRITICALITY		reject		TYPE	DedicatedMeasurementObjectType-DM-Rqst		PRESENCE	mandatory	} |
	{ ID 	id-DedicatedMeasurementType						CRITICALITY		reject		TYPE	DedicatedMeasurementType					PRESENCE	mandatory	} |
	{ ID	id-MeasurementFilterCoefficient					CRITICALITY		reject		TYPE	MeasurementFilterCoefficient					PRESENCE	optional	} |
	{ ID 	id-ReportCharacteristics						CRITICALITY		reject		TYPE	ReportCharacteristics						PRESENCE	mandatory	} |
	{ ID 	id-CFNReportingIndicator						CRITICALITY		reject		TYPE	FNReportingIndicator						PRESENCE	mandatory	} |
    { ID    id-CFN                                          CRITICALITY     reject      TYPE    CFN                							PRESENCE optional	} ,
	...
}

DedicatedMeasurementInitiationRequest-Extensions NBAP-PROTOCOL-EXTENSION ::= {
	...
}

DedicatedMeasurementObjectType-DM-Rqst ::= CHOICE {
	rL							RL-DM-Rqst,
	rLS							RL-Set-DM-Rqst, 		-- for FDD only
	all-RL						AllRL-DM-Rqst,
	all-RLS						AllRL-Set-DM-Rqst, 		-- for FDD only
	...
}

RL-DM-Rqst ::= SEQUENCE {
 	rL-InformationList					RL-InformationList-DM-Rqst,
	iE-Extensions						ProtocolExtensionContainer { { RLItem-DM-Rqst-ExtIEs } }		OPTIONAL,
	...		
}

RLItem-DM-Rqst-ExtIEs  NBAP-PROTOCOL-EXTENSION ::= {
	...
}

RL-InformationList-DM-Rqst ::= SEQUENCE (SIZE (1..maxNrOfRLs)) OF ProtocolIE-Single-Container {{ RL-InformationItemIE-DM-Rqst }}

RL-InformationItemIE-DM-Rqst NBAP-PROTOCOL-IES ::= {
	{ ID id-RL-InformationItem-DM-Rqst   CRITICALITY reject	TYPE RL-InformationItem-DM-Rqst		PRESENCE mandatory }
}

RL-InformationItem-DM-Rqst ::= SEQUENCE {
		rL-ID							RL-ID,	
		dPCH-ID							DPCH-ID				OPTIONAL, -- for TDD only
		iE-Extensions					ProtocolExtensionContainer { { RL-InformationItem-DM-Rqst-ExtIEs } }		OPTIONAL,
		...		
	}

RL-InformationItem-DM-Rqst-ExtIEs  NBAP-PROTOCOL-EXTENSION ::= {
	{ ID id-PUSCH-Info-DM-Rqst		CRITICALITY reject				EXTENSION	PUSCH-Info-DM-Rqst		PRESENCE optional},
	-- TDD only
	...
}

PUSCH-Info-DM-Rqst ::= SEQUENCE (SIZE (1..maxNrOfPUSCHs)) OF PUSCH-ID

RL-Set-DM-Rqst ::= SEQUENCE {
	rL-Set-InformationList-DM-Rqst			RL-Set-InformationList-DM-Rqst,
	iE-Extensions							ProtocolExtensionContainer { { RL-SetItem-DM-Rqst-ExtIEs } }		OPTIONAL,
	...		
}

RL-SetItem-DM-Rqst-ExtIEs  NBAP-PROTOCOL-EXTENSION ::= {
	...
}

RL-Set-InformationList-DM-Rqst					::= SEQUENCE (SIZE(1..maxNrOfRLSets)) OF RL-Set-InformationItem-DM-Rqst

RL-Set-InformationItem-DM-Rqst ::= SEQUENCE {
	rL-Set-ID						RL-Set-ID,
	iE-Extensions					ProtocolExtensionContainer { { RL-Set-InformationItem-DM-Rqst-ExtIEs} } OPTIONAL,
	...
}

RL-Set-InformationItem-DM-Rqst-ExtIEs NBAP-PROTOCOL-EXTENSION ::= {
	...
}

AllRL-DM-Rqst ::= NULL


AllRL-Set-DM-Rqst ::= NULL

-- **************************************************************
--
-- DEDICATED MEASUREMENT INITIATION RESPONSE
--
-- **************************************************************

DedicatedMeasurementInitiationResponse ::= SEQUENCE {
	protocolIEs				ProtocolIE-Container	{{DedicatedMeasurementInitiationResponse-IEs}},
	protocolExtensions		ProtocolExtensionContainer	{{DedicatedMeasurementInitiationResponse-Extensions}}		OPTIONAL,
	...
}

DedicatedMeasurementInitiationResponse-IEs NBAP-PROTOCOL-IES ::= {
	{ ID	id-CRNC-CommunicationContextID					CRITICALITY		ignore		TYPE	CRNC-CommunicationContextID					PRESENCE	mandatory	} |
	{ ID	id-MeasurementID								CRITICALITY		ignore		TYPE	MeasurementID								PRESENCE	mandatory	} |
	{ ID	id-DedicatedMeasurementObjectType-DM-Rsp		CRITICALITY		ignore		TYPE	DedicatedMeasurementObjectType-DM-Rsp		PRESENCE	optional	} |
	{ ID	id-CriticalityDiagnostics						CRITICALITY		ignore		TYPE	CriticalityDiagnostics						PRESENCE	optional	},
	...
}

DedicatedMeasurementInitiationResponse-Extensions NBAP-PROTOCOL-EXTENSION ::= {
	...
}

DedicatedMeasurementObjectType-DM-Rsp ::= CHOICE {
	rL							RL-DM-Rsp,
	rLS							RL-Set-DM-Rsp, 	-- for FDD only
	all-RL						RL-DM-Rsp,
	all-RLS						RL-Set-DM-Rsp, 	-- for FDD only
	...
}

RL-DM-Rsp ::= SEQUENCE {
	rL-InformationList-DM-Rsp			RL-InformationList-DM-Rsp,
	iE-Extensions						ProtocolExtensionContainer { { RLItem-DM-Rsp-ExtIEs } }		OPTIONAL,
	...
}

RLItem-DM-Rsp-ExtIEs  NBAP-PROTOCOL-EXTENSION ::= {
	...
}

RL-InformationList-DM-Rsp ::= SEQUENCE (SIZE (1..maxNrOfRLs)) OF ProtocolIE-Single-Container {{ RL-InformationItemIE-DM-Rsp }}

RL-InformationItemIE-DM-Rsp NBAP-PROTOCOL-IES ::= {
	{ ID id-RL-InformationItem-DM-Rsp   CRITICALITY ignore	TYPE RL-InformationItem-DM-Rsp		PRESENCE mandatory }
}

RL-InformationItem-DM-Rsp ::= SEQUENCE {
	rL-ID								RL-ID,
	dPCH-ID								DPCH-ID			OPTIONAL, 	-- for TDD only
	dedicatedMeasurementValue			DedicatedMeasurementValue,
    cFN                                 CFN             OPTIONAL,
	iE-Extensions						ProtocolExtensionContainer { { RL-InformationItem-DM-Rsp-ExtIEs } }		OPTIONAL,
	...
}

RL-InformationItem-DM-Rsp-ExtIEs  NBAP-PROTOCOL-EXTENSION ::= {
	{ID id-PUSCH-Info-DM-Rsp		CRITICALITY reject				EXTENSION	PUSCH-Info-DM-Rsp		PRESENCE optional},
	-- TDD only
	...
}

PUSCH-Info-DM-Rsp ::= SEQUENCE (SIZE (1..maxNrOfPUSCHs)) OF PUSCH-ID

RL-Set-DM-Rsp ::= SEQUENCE {
	rL-Set-InformationList-DM-Rsp		RL-Set-InformationList-DM-Rsp,
	iE-Extensions						ProtocolExtensionContainer { { RL-SetItem-DM-Rsp-ExtIEs } }		OPTIONAL,
	...
}

RL-SetItem-DM-Rsp-ExtIEs  NBAP-PROTOCOL-EXTENSION ::= {
	...
}

RL-Set-InformationList-DM-Rsp ::= SEQUENCE (SIZE (1..maxNrOfRLSets)) OF ProtocolIE-Single-Container {{ RL-Set-InformationItemIE-DM-Rsp }}

RL-Set-InformationItemIE-DM-Rsp NBAP-PROTOCOL-IES ::= {
	{ ID id-RL-Set-InformationItem-DM-Rsp		CRITICALITY ignore		TYPE 	RL-Set-InformationItem-DM-Rsp	PRESENCE mandatory}
}

RL-Set-InformationItem-DM-Rsp ::= SEQUENCE {
	rL-Set-ID						RL-Set-ID,
	dedicatedMeasurementValue		DedicatedMeasurementValue,
    cFN								CFN             OPTIONAL,
	iE-Extensions					ProtocolExtensionContainer { { RL-Set-InformationItem-DM-Rsp-ExtIEs} } OPTIONAL,
	...
}

RL-Set-InformationItem-DM-Rsp-ExtIEs NBAP-PROTOCOL-EXTENSION ::= {
	...
}

-- **************************************************************
--
-- DEDICATED MEASUREMENT INITIATION FAILURE
--
-- **************************************************************

DedicatedMeasurementInitiationFailure ::= SEQUENCE {
	protocolIEs				ProtocolIE-Container	{{DedicatedMeasurementInitiationFailure-IEs}},
	protocolExtensions		ProtocolExtensionContainer	{{DedicatedMeasurementInitiationFailure-Extensions}}		OPTIONAL,
	...
}

DedicatedMeasurementInitiationFailure-IEs NBAP-PROTOCOL-IES ::= {
	{ ID	id-CRNC-CommunicationContextID			CRITICALITY		ignore			TYPE	CRNC-CommunicationContextID		PRESENCE	mandatory	} |
	{ ID	id-MeasurementID						CRITICALITY		ignore			TYPE	MeasurementID					PRESENCE	mandatory	} |
	{ ID	id-Cause								CRITICALITY		ignore			TYPE	Cause							PRESENCE	mandatory	} |
	{ ID	id-CriticalityDiagnostics				CRITICALITY		ignore			TYPE	CriticalityDiagnostics			PRESENCE	optional	},
	...
}

DedicatedMeasurementInitiationFailure-Extensions NBAP-PROTOCOL-EXTENSION ::= {
	...
}

-- **************************************************************
--
-- DEDICATED MEASUREMENT REPORT
--
-- **************************************************************

DedicatedMeasurementReport ::= SEQUENCE {
	protocolIEs				ProtocolIE-Container	{{DedicatedMeasurementReport-IEs}},
	protocolExtensions		ProtocolExtensionContainer	{{DedicatedMeasurementReport-Extensions}}		OPTIONAL,
	...
}

DedicatedMeasurementReport-IEs NBAP-PROTOCOL-IES ::= {
	{ ID	id-CRNC-CommunicationContextID						CRITICALITY		ignore		TYPE	CRNC-CommunicationContextID					PRESENCE	mandatory	} |
	{ ID	id-MeasurementID									CRITICALITY		ignore		TYPE	MeasurementID								PRESENCE	mandatory	} |
	{ ID	id-DedicatedMeasurementObjectType-DM-Rprt			CRITICALITY		ignore		TYPE	DedicatedMeasurementObjectType-DM-Rprt		PRESENCE	mandatory	} ,
	...
}

DedicatedMeasurementReport-Extensions NBAP-PROTOCOL-EXTENSION ::= {
	...
}

DedicatedMeasurementObjectType-DM-Rprt ::= CHOICE {
 	rL									RL-DM-Rprt,
	rLS									RL-Set-DM-Rprt, 		-- for FDD only
 	all-RL								RL-DM-Rprt,
	all-RLS								RL-Set-DM-Rprt, 		-- for FDD only
	...
}

RL-DM-Rprt ::= SEQUENCE {
	rL-InformationList-DM-Rprt			RL-InformationList-DM-Rprt,
	iE-Extensions						ProtocolExtensionContainer { { RLItem-DM-Rprt-ExtIEs } }		OPTIONAL,
	...
}

RLItem-DM-Rprt-ExtIEs  NBAP-PROTOCOL-EXTENSION ::= {
	...
}

RL-InformationList-DM-Rprt ::= SEQUENCE (SIZE (1..maxNrOfRLs)) OF ProtocolIE-Single-Container {{ RL-InformationItemIE-DM-Rprt }}

RL-InformationItemIE-DM-Rprt NBAP-PROTOCOL-IES ::= {
	{ ID id-RL-InformationItem-DM-Rprt   CRITICALITY ignore	TYPE RL-InformationItem-DM-Rprt		PRESENCE mandatory }
}

RL-InformationItem-DM-Rprt ::= SEQUENCE {
	rL-ID							RL-ID,
	dPCH-ID							DPCH-ID		OPTIONAL, 		-- for TDD only
	dedicatedMeasurementValueInformation	DedicatedMeasurementValueInformation,
	iE-Extensions					ProtocolExtensionContainer { { RL-InformationItem-DM-Rprt-ExtIEs } }		OPTIONAL,
	...
}

RL-InformationItem-DM-Rprt-ExtIEs  NBAP-PROTOCOL-EXTENSION ::= {
	{ID id-PUSCH-Info-DM-Rprt		CRITICALITY reject				EXTENSION	PUSCH-Info-DM-Rprt		PRESENCE optional},
	-- TDD only
	...
}

PUSCH-Info-DM-Rprt ::= SEQUENCE (SIZE (0..maxNrOfPUSCHs)) OF PUSCH-ID

RL-Set-DM-Rprt ::= SEQUENCE {
	rL-Set-InformationList-DM-Rprt		RL-Set-InformationList-DM-Rprt,
	iE-Extensions						ProtocolExtensionContainer { { RL-SetItem-DM-Rprt-ExtIEs } }		OPTIONAL,
	...
}

RL-SetItem-DM-Rprt-ExtIEs  NBAP-PROTOCOL-EXTENSION ::= {
	...
}

RL-Set-InformationList-DM-Rprt ::= SEQUENCE (SIZE (1..maxNrOfRLSets)) OF ProtocolIE-Single-Container {{ RL-Set-InformationItemIE-DM-Rprt }}

RL-Set-InformationItemIE-DM-Rprt NBAP-PROTOCOL-IES ::= {
	{ ID id-RL-Set-InformationItem-DM-Rprt	CRITICALITY ignore	TYPE RL-Set-InformationItem-DM-Rprt		PRESENCE mandatory	}
}

RL-Set-InformationItem-DM-Rprt ::= SEQUENCE {
	rL-Set-ID						RL-Set-ID,
	dedicatedMeasurementValueInformation	DedicatedMeasurementValueInformation,
	iE-Extensions					ProtocolExtensionContainer { { RL-Set-InformationItem-DM-Rprt-ExtIEs} } OPTIONAL,
	...
}

RL-Set-InformationItem-DM-Rprt-ExtIEs NBAP-PROTOCOL-EXTENSION ::= {
	...
}

-- **************************************************************
--
-- DEDICATED MEASUREMENT TERMINATION REQUEST
--
-- **************************************************************

DedicatedMeasurementTerminationRequest ::= SEQUENCE {
	protocolIEs				ProtocolIE-Container	{{DedicatedMeasurementTerminationRequest-IEs}},
	protocolExtensions		ProtocolExtensionContainer	{{DedicatedMeasurementTerminationRequest-Extensions}}		OPTIONAL,
	...
}

DedicatedMeasurementTerminationRequest-IEs NBAP-PROTOCOL-IES ::= {
	{ ID	id-NodeB-CommunicationContextID			CRITICALITY		ignore			TYPE	NodeB-CommunicationContextID		PRESENCE	mandatory	} |
	{ ID	id-MeasurementID						CRITICALITY		ignore			TYPE	MeasurementID						PRESENCE	mandatory	},
	...
}

DedicatedMeasurementTerminationRequest-Extensions NBAP-PROTOCOL-EXTENSION ::= {
	...
}

-- **************************************************************
--
-- DEDICATED MEASUREMENT FAILURE INDICATION
--
-- **************************************************************

DedicatedMeasurementFailureIndication ::= SEQUENCE {
	protocolIEs				ProtocolIE-Container	{{DedicatedMeasurementFailureIndication-IEs}},
	protocolExtensions		ProtocolExtensionContainer	{{DedicatedMeasurementFailureIndication-Extensions}}		OPTIONAL,
	...
}

DedicatedMeasurementFailureIndication-IEs NBAP-PROTOCOL-IES ::= {
	{ ID	id-CRNC-CommunicationContextID		CRITICALITY		ignore		TYPE	CRNC-CommunicationContextID		PRESENCE	mandatory	} |
	{ ID	id-MeasurementID					CRITICALITY		ignore		TYPE	MeasurementID					PRESENCE	mandatory	} |
	{ ID	id-Cause							CRITICALITY		ignore		TYPE	Cause							PRESENCE	mandatory	},
	...
}

DedicatedMeasurementFailureIndication-Extensions NBAP-PROTOCOL-EXTENSION ::= {
	...
}

-- **************************************************************
--
-- RADIO LINK FAILURE INDICATION
--
-- **************************************************************

RadioLinkFailureIndication ::= SEQUENCE {
	protocolIEs				ProtocolIE-Container	{{RadioLinkFailureIndication-IEs}},
	protocolExtensions		ProtocolExtensionContainer	{{RadioLinkFailureIndication-Extensions}}		OPTIONAL,
	...
}

RadioLinkFailureIndication-IEs NBAP-PROTOCOL-IES ::= {
	{ ID	id-CRNC-CommunicationContextID				CRITICALITY		ignore			TYPE	CRNC-CommunicationContextID				PRESENCE	mandatory	} |
	{ ID	id-Reporting-Object-RL-FailureInd			CRITICALITY		ignore			TYPE	Reporting-Object-RL-FailureInd		PRESENCE	mandatory	} ,
	...
}

RadioLinkFailureIndication-Extensions NBAP-PROTOCOL-EXTENSION ::= {
	...
}

Reporting-Object-RL-FailureInd ::= CHOICE {
	rL						RL-RL-FailureInd,
	rL-Set					RL-Set-RL-FailureInd, --FDD only
	...,
	cCTrCH					CCTrCH-RL-FailureInd --TDD only
}

RL-RL-FailureInd ::= SEQUENCE {
	rL-InformationList-RL-FailureInd		RL-InformationList-RL-FailureInd,
	iE-Extensions							ProtocolExtensionContainer { { RLItem-RL-FailureInd-ExtIEs } }		OPTIONAL,
	...
 }

RLItem-RL-FailureInd-ExtIEs NBAP-PROTOCOL-EXTENSION ::= {
	...
}

RL-InformationList-RL-FailureInd ::= SEQUENCE (SIZE (1..maxNrOfRLs)) OF ProtocolIE-Single-Container {{ RL-InformationItemIE-RL-FailureInd}}

RL-InformationItemIE-RL-FailureInd NBAP-PROTOCOL-IES ::= {
 	{ ID	id-RL-InformationItem-RL-FailureInd			CRITICALITY		ignore			TYPE	RL-InformationItem-RL-FailureInd			PRESENCE	mandatory}
 }

RL-InformationItem-RL-FailureInd ::= SEQUENCE {
 	rL-ID										RL-ID,
 	cause										Cause,
	iE-Extensions								ProtocolExtensionContainer { { RL-InformationItem-RL-FailureInd-ExtIEs } }		OPTIONAL,
	...
 }

RL-InformationItem-RL-FailureInd-ExtIEs NBAP-PROTOCOL-EXTENSION ::= {
	...
}

RL-Set-RL-FailureInd ::= SEQUENCE {
	rL-Set-InformationList-RL-FailureInd		RL-Set-InformationList-RL-FailureInd,
	iE-Extensions							ProtocolExtensionContainer { { RL-SetItem-RL-FailureInd-ExtIEs } }		OPTIONAL,
	...
 }

RL-SetItem-RL-FailureInd-ExtIEs NBAP-PROTOCOL-EXTENSION ::= {
	...
}

RL-Set-InformationList-RL-FailureInd ::= SEQUENCE (SIZE (1..maxNrOfRLSets)) OF ProtocolIE-Single-Container {{ RL-Set-InformationItemIE-RL-FailureInd }}

RL-Set-InformationItemIE-RL-FailureInd NBAP-PROTOCOL-IES ::= {
 	{ ID id-RL-Set-InformationItem-RL-FailureInd	CRITICALITY ignore		TYPE RL-Set-InformationItem-RL-FailureInd		PRESENCE mandatory	}
}

RL-Set-InformationItem-RL-FailureInd ::= SEQUENCE {
 	rL-Set-ID				RL-Set-ID,
 	cause					Cause,
	iE-Extensions			ProtocolExtensionContainer { { RL-Set-InformationItem-RL-FailureInd-ExtIEs} } OPTIONAL,
	...
}

RL-Set-InformationItem-RL-FailureInd-ExtIEs NBAP-PROTOCOL-EXTENSION ::= {
	...
}

CCTrCH-RL-FailureInd ::= SEQUENCE {
	rL-ID										RL-ID,
	cCTrCH-InformationList-RL-FailureInd		CCTrCH-InformationList-RL-FailureInd,
	iE-Extensions							ProtocolExtensionContainer { { CCTrCHItem-RL-FailureInd-ExtIEs } }		OPTIONAL,
	...
 }

CCTrCHItem-RL-FailureInd-ExtIEs NBAP-PROTOCOL-EXTENSION ::= {
	...
}

CCTrCH-InformationList-RL-FailureInd ::= SEQUENCE (SIZE (1..maxNrOfCCTrCHs)) OF ProtocolIE-Single-Container {{ CCTrCH-InformationItemIE-RL-FailureInd}}

CCTrCH-InformationItemIE-RL-FailureInd NBAP-PROTOCOL-IES ::= {
 	{ ID	id-CCTrCH-InformationItem-RL-FailureInd			CRITICALITY		ignore			TYPE	CCTrCH-InformationItem-RL-FailureInd			PRESENCE	mandatory}
 }

CCTrCH-InformationItem-RL-FailureInd ::= SEQUENCE {
 	cCTrCH-ID									CCTrCH-ID,
	cause										Cause,
	iE-Extensions								ProtocolExtensionContainer { { CCTrCH-InformationItem-RL-FailureInd-ExtIEs } }		OPTIONAL,
	...
 }

CCTrCH-InformationItem-RL-FailureInd-ExtIEs NBAP-PROTOCOL-EXTENSION ::= {
	...
}

-- **************************************************************
--
-- RADIO LINK PREEMPTION REQUIRED INDICATION
--
-- **************************************************************

RadioLinkPreemptionRequiredIndication ::= SEQUENCE {
	protocolIEs                     ProtocolIE-Container       {{RadioLinkPreemptionRequiredIndication-IEs}},
	protocolExtensions              ProtocolExtensionContainer {{RadioLinkPreemptionRequiredIndication-Extensions}}                   OPTIONAL,
	...
}

RadioLinkPreemptionRequiredIndication-IEs NBAP-PROTOCOL-IES ::= {
	{ ID	id-CRNC-CommunicationContextID					CRITICALITY		ignore			TYPE	CRNC-CommunicationContextID				PRESENCE	mandatory		} |
	{ ID id-RL-InformationList-RL-PreemptRequiredInd	CRITICALITY ignore	TYPE RL-InformationList-RL-PreemptRequiredInd		PRESENCE optional	},
	...
}

RadioLinkPreemptionRequiredIndication-Extensions NBAP-PROTOCOL-EXTENSION ::= {
	...
}

RL-InformationList-RL-PreemptRequiredInd			::= SEQUENCE (SIZE (1..maxNrOfRLs)) OF ProtocolIE-Single-Container { {RL-InformationItemIE-RL-PreemptRequiredInd}}

RL-InformationItemIE-RL-PreemptRequiredInd NBAP-PROTOCOL-IES ::= {
	{ ID id-RL-InformationItem-RL-PreemptRequiredInd		CRITICALITY ignore	TYPE RL-InformationItem-RL-PreemptRequiredInd		PRESENCE mandatory	},
	...
}

RL-InformationItem-RL-PreemptRequiredInd::= SEQUENCE {
	rL-ID						RL-ID,
	iE-Extensions				ProtocolExtensionContainer { {RL-InformationItem-RL-PreemptRequiredInd-ExtIEs} } OPTIONAL,
	...
}

RL-InformationItem-RL-PreemptRequiredInd-ExtIEs NBAP-PROTOCOL-EXTENSION ::= {
	...
}

-- **************************************************************
--
-- RADIO LINK RESTORE INDICATION
--
-- **************************************************************

RadioLinkRestoreIndication ::= SEQUENCE {
	protocolIEs				ProtocolIE-Container	{{RadioLinkRestoreIndication-IEs}},
	protocolExtensions		ProtocolExtensionContainer	{{RadioLinkRestoreIndication-Extensions}}		OPTIONAL,
	...
}

RadioLinkRestoreIndication-IEs NBAP-PROTOCOL-IES ::= {
	{ ID	id-CRNC-CommunicationContextID				CRITICALITY		ignore			TYPE	CRNC-CommunicationContextID				PRESENCE	mandatory	} |
	{ ID	id-Reporting-Object-RL-RestoreInd			CRITICALITY		ignore			TYPE	Reporting-Object-RL-RestoreInd		PRESENCE	mandatory	},
	...
}

RadioLinkRestoreIndication-Extensions NBAP-PROTOCOL-EXTENSION ::= {
	...
}

Reporting-Object-RL-RestoreInd ::= CHOICE {
	rL						RL-RL-RestoreInd, --TDD only
	rL-Set					RL-Set-RL-RestoreInd, --FDD only
	...,
	cCTrCH					CCTrCH-RL-RestoreInd --TDD only
}

RL-RL-RestoreInd ::= SEQUENCE {
	rL-InformationList-RL-RestoreInd		RL-InformationList-RL-RestoreInd,
	iE-Extensions							ProtocolExtensionContainer { { RLItem-RL-RestoreInd-ExtIEs } }		OPTIONAL,
	...
 }

RLItem-RL-RestoreInd-ExtIEs NBAP-PROTOCOL-EXTENSION ::= {
	...
}

RL-InformationList-RL-RestoreInd ::= SEQUENCE (SIZE (1..maxNrOfRLs)) OF ProtocolIE-Single-Container {{RL-InformationItemIE-RL-RestoreInd}}

RL-InformationItemIE-RL-RestoreInd NBAP-PROTOCOL-IES ::= {
 	{ ID	id-RL-InformationItem-RL-RestoreInd			CRITICALITY		ignore			TYPE	RL-InformationItem-RL-RestoreInd			PRESENCE	mandatory}
 }

RL-InformationItem-RL-RestoreInd ::= SEQUENCE {
 	rL-ID									RL-ID,
	iE-Extensions							ProtocolExtensionContainer { { RL-InformationItem-RL-RestoreInd-ExtIEs } }		OPTIONAL,
	...
 }

RL-InformationItem-RL-RestoreInd-ExtIEs NBAP-PROTOCOL-EXTENSION ::= {
	...
}

RL-Set-RL-RestoreInd ::= SEQUENCE {
	rL-Set-InformationList-RL-RestoreInd	RL-Set-InformationList-RL-RestoreInd,
	iE-Extensions							ProtocolExtensionContainer { { RL-SetItem-RL-RestoreInd-ExtIEs } }		OPTIONAL,
	...
 }

RL-SetItem-RL-RestoreInd-ExtIEs NBAP-PROTOCOL-EXTENSION ::= {
	...
}

RL-Set-InformationList-RL-RestoreInd ::= SEQUENCE (SIZE (1..maxNrOfRLSets)) OF ProtocolIE-Single-Container {{ RL-Set-InformationItemIE-RL-RestoreInd }}

RL-Set-InformationItemIE-RL-RestoreInd NBAP-PROTOCOL-IES ::= {
 	{ ID id-RL-Set-InformationItem-RL-RestoreInd	CRITICALITY ignore		TYPE RL-Set-InformationItem-RL-RestoreInd	PRESENCE mandatory	}
 }

RL-Set-InformationItem-RL-RestoreInd ::= SEQUENCE {
 	rL-Set-ID				RL-Set-ID,
 	iE-Extensions			ProtocolExtensionContainer { { RL-Set-InformationItem-RL-RestoreInd-ExtIEs} } OPTIONAL,
	...
}

RL-Set-InformationItem-RL-RestoreInd-ExtIEs NBAP-PROTOCOL-EXTENSION ::= {
	...
}

CCTrCH-RL-RestoreInd ::= SEQUENCE {
	rL-ID										RL-ID,
	cCTrCH-InformationList-RL-RestoreInd		CCTrCH-InformationList-RL-RestoreInd,
	iE-Extensions							ProtocolExtensionContainer { { CCTrCHItem-RL-RestoreInd-ExtIEs } }		OPTIONAL,
	...
 }

CCTrCHItem-RL-RestoreInd-ExtIEs NBAP-PROTOCOL-EXTENSION ::= {
	...
}

CCTrCH-InformationList-RL-RestoreInd ::= SEQUENCE (SIZE (1..maxNrOfCCTrCHs)) OF ProtocolIE-Single-Container {{ CCTrCH-InformationItemIE-RL-RestoreInd}}

CCTrCH-InformationItemIE-RL-RestoreInd NBAP-PROTOCOL-IES ::= {
 	{ ID	id-CCTrCH-InformationItem-RL-RestoreInd			CRITICALITY		ignore			TYPE	CCTrCH-InformationItem-RL-RestoreInd			PRESENCE	mandatory}
 }

CCTrCH-InformationItem-RL-RestoreInd ::= SEQUENCE {
 	cCTrCH-ID										CCTrCH-ID,
	iE-Extensions								ProtocolExtensionContainer { { CCTrCH-InformationItem-RL-RestoreInd-ExtIEs } }		OPTIONAL,
	...
 }

CCTrCH-InformationItem-RL-RestoreInd-ExtIEs NBAP-PROTOCOL-EXTENSION ::= {
	...
}

-- **************************************************************
--
-- COMPRESSED MODE COMMAND FDD
--
-- **************************************************************

CompressedModeCommand ::= SEQUENCE {
	protocolIEs				ProtocolIE-Container	{{CompressedModeCommand-IEs}},
	protocolExtensions		ProtocolExtensionContainer	{{CompressedModeCommand-Extensions}}                   OPTIONAL,
	...
}

CompressedModeCommand-IEs NBAP-PROTOCOL-IES ::= {
	{ ID 	id-NodeB-CommunicationContextID			CRITICALITY 		ignore		TYPE 	NodeB-CommunicationContextID				PRESENCE 	mandatory	} |
	{ ID 	id-Active-Pattern-Sequence-Information	CRITICALITY 		ignore		TYPE 	Active-Pattern-Sequence-Information		PRESENCE mandatory },
	...
}

CompressedModeCommand-Extensions NBAP-PROTOCOL-EXTENSION ::= {
	...
}


-- **************************************************************
--
-- ERROR INDICATION
--
-- **************************************************************

ErrorIndication ::= SEQUENCE {
	protocolIEs				ProtocolIE-Container	{{ErrorIndication-IEs}},
	protocolExtensions		ProtocolExtensionContainer	{{ErrorIndication-Extensions}}		OPTIONAL,
	...
}

ErrorIndication-IEs NBAP-PROTOCOL-IES ::= {
	{ ID	id-CRNC-CommunicationContextID		CRITICALITY		ignore			TYPE 	CRNC-CommunicationContextID			PRESENCE	optional	} |
	{ ID	id-NodeB-CommunicationContextID		CRITICALITY		ignore			TYPE 	NodeB-CommunicationContextID		PRESENCE	optional	} |
	{ ID	id-Cause							CRITICALITY		ignore			TYPE	Cause								PRESENCE	optional	} |
	{ ID	id-CriticalityDiagnostics			CRITICALITY		ignore			TYPE	CriticalityDiagnostics				PRESENCE	optional	},
	...
}

ErrorIndication-Extensions NBAP-PROTOCOL-EXTENSION ::= {
	...
}

-- **************************************************************
--
-- PRIVATE MESSAGE
--
-- **************************************************************

PrivateMessage ::= SEQUENCE {
	privateIEs		PrivateIE-Container	{{PrivateMessage-IEs}},
	...
}

PrivateMessage-IEs NBAP-PRIVATE-IES ::= {
	...
}

-- **************************************************************
--
-- PHYSICAL SHARED CHANNEL RECONFIGURATION REQUEST FDD
--
-- **************************************************************

PhysicalSharedChannelReconfigurationRequestFDD ::= SEQUENCE {
	protocolIEs			ProtocolIE-Container  {{PhysicalSharedChannelReconfigurationRequestFDD-IEs}},
	protocolExtensions    ProtocolExtensionContainer {{PhysicalSharedChannelReconfigurationRequestFDD-Extensions}}    OPTIONAL,
	...
}

PhysicalSharedChannelReconfigurationRequestFDD-IEs NBAP-PROTOCOL-IES ::= {
	{ ID	id-C-ID										CRITICALITY		reject			TYPE	C-ID								PRESENCE	mandatory	} |
	{ ID	id-SFN										CRITICALITY		reject			TYPE	SFN								PRESENCE	optional} |
	{ ID	id-HS-PDSCH-HS-SCCH-MaxPower-PSCH-ReconfRqst	CRITICALITY		reject		TYPE 	MaximumTransmissionPower						PRESENCE	optional	} |
	{ ID	id-HS-PDSCH-HS-SCCH-ScramblingCode-PSCH-ReconfRqst	CRITICALITY		reject	TYPE 	DL-ScramblingCode								PRESENCE	optional	} |
	{ ID	id-HS-PDSCH-FDD-Code-Information-PSCH-ReconfRqst	CRITICALITY		reject	TYPE 	HS-PDSCH-FDD-Code-Information				PRESENCE	optional	} |
	{ ID	id-HS-SCCH-FDD-Code-Information-PSCH-ReconfRqst		CRITICALITY		reject	TYPE 	HS-SCCH-FDD-Code-Information					PRESENCE	optional	},
	...
}

PhysicalSharedChannelReconfigurationRequestFDD-Extensions NBAP-PROTOCOL-EXTENSION ::= {
	...
}

-- **************************************************************
--
-- PHYSICAL SHARED CHANNEL RECONFIGURATION REQUEST TDD
--
-- **************************************************************

PhysicalSharedChannelReconfigurationRequestTDD ::= SEQUENCE {
	protocolIEs			ProtocolIE-Container  {{PhysicalSharedChannelReconfigurationRequestTDD-IEs}},
	protocolExtensions    ProtocolExtensionContainer {{PhysicalSharedChannelReconfigurationRequestTDD-Extensions}}    OPTIONAL,
	...
}

PhysicalSharedChannelReconfigurationRequestTDD-IEs NBAP-PROTOCOL-IES ::= {
	{ ID	id-C-ID										CRITICALITY		reject			TYPE	C-ID												PRESENCE	mandatory	} |
	{ ID	id-SFN										CRITICALITY		reject			TYPE	SFN													PRESENCE	optional} |
	{ ID	id-PDSCHSets-AddList-PSCH-ReconfRqst		CRITICALITY		reject			TYPE 	PDSCHSets-AddList-PSCH-ReconfRqst			PRESENCE	optional	} |
	{ ID	id-PDSCHSets-ModifyList-PSCH-ReconfRqst		CRITICALITY		reject			TYPE 	PDSCHSets-ModifyList-PSCH-ReconfRqst		PRESENCE	optional	} |
	{ ID	id-PDSCHSets-DeleteList-PSCH-ReconfRqst		CRITICALITY		reject			TYPE 	PDSCHSets-DeleteList-PSCH-ReconfRqst		PRESENCE	optional	} |
	{ ID	id-PUSCHSets-AddList-PSCH-ReconfRqst		CRITICALITY		reject			TYPE 	PUSCHSets-AddList-PSCH-ReconfRqst			PRESENCE	optional	} |
	{ ID	id-PUSCHSets-ModifyList-PSCH-ReconfRqst		CRITICALITY		reject			TYPE 	PUSCHSets-ModifyList-PSCH-ReconfRqst		PRESENCE	optional	} |
	{ ID	id-PUSCHSets-DeleteList-PSCH-ReconfRqst		CRITICALITY		reject			TYPE 	PUSCHSets-DeleteList-PSCH-ReconfRqst		PRESENCE	optional	},
	...
}

PhysicalSharedChannelReconfigurationRequestTDD-Extensions NBAP-PROTOCOL-EXTENSION ::= {
	{ ID	id-HS-PDSCH-TDD-Information-PSCH-ReconfRqst			CRITICALITY		reject		EXTENSION HS-PDSCH-TDD-Information-PSCH-ReconfRqst		PRESENCE	optional	} |
	{ ID	id-Add-To-HS-SCCH-Resource-Pool-PSCH-ReconfRqst		CRITICALITY		reject		EXTENSION Add-To-HS-SCCH-Resource-Pool-PSCH-ReconfRqst			PRESENCE	optional	} |
	{ ID	id-Modify-HS-SCCH-Resource-Pool-PSCH-ReconfRqst		CRITICALITY		reject		EXTENSION Modify-HS-SCCH-Resource-Pool-PSCH-ReconfRqst			PRESENCE	optional	} |
	{ ID	id-Delete-From-HS-SCCH-Resource-Pool-PSCH-ReconfRqst	CRITICALITY		reject		EXTENSION Delete-From-HS-SCCH-Resource-Pool-PSCH-ReconfRqst		PRESENCE	optional	},
	...
}

PDSCHSets-AddList-PSCH-ReconfRqst ::= SEQUENCE (SIZE (1..maxNrOfPDSCHSets)) OF PDSCHSets-AddItem-PSCH-ReconfRqst

PDSCHSets-AddItem-PSCH-ReconfRqst	 ::= SEQUENCE {
	pDSCHSet-ID									PDSCHSet-ID,
	pDSCH-InformationList						PDSCH-Information-AddList-PSCH-ReconfRqst 	OPTIONAL,
	iE-Extensions								ProtocolExtensionContainer { {PDSCHSets-AddItem-PSCH-ReconfRqst-ExtIEs} }		OPTIONAL,
	...
}

PDSCHSets-AddItem-PSCH-ReconfRqst-ExtIEs  NBAP-PROTOCOL-EXTENSION ::= {
	{ID id-PDSCH-AddInformation-LCR-PSCH-ReconfRqst 	CRITICALITY	reject		EXTENSION 	PDSCH-AddInformation-LCR-AddItem-PSCH-ReconfRqst			PRESENCE	optional}, -- Mandatory for 1.28Mcps TDD
	...
}

PDSCH-Information-AddList-PSCH-ReconfRqst ::= ProtocolIE-Single-Container {{ PDSCH-Information-AddListIEs-PSCH-ReconfRqst }}
-- Mandatory for 3.84Mcps TDD, Not Applicable to 1.28Mcps TDD

PDSCH-Information-AddListIEs-PSCH-ReconfRqst	NBAP-PROTOCOL-IES ::= { 
	{ID id-PDSCH-Information-AddListIE-PSCH-ReconfRqst 	CRITICALITY	reject		TYPE 	PDSCH-Information-AddItem-PSCH-ReconfRqst			PRESENCE	mandatory}
}

PDSCH-Information-AddItem-PSCH-ReconfRqst ::= SEQUENCE {
	repetitionPeriod						RepetitionPeriod,
	repetitionLength						RepetitionLength,
	tdd-PhysicalChannelOffset					TDD-PhysicalChannelOffset,
	dL-Timeslot-InformationAddList-PSCH-ReconfRqst				DL-Timeslot-InformationAddList-PSCH-ReconfRqst,
	iE-Extensions								ProtocolExtensionContainer { {PDSCH-Information-AddItem-PSCH-ReconfRqst-ExtIEs} }		OPTIONAL,
	...
	}

PDSCH-Information-AddItem-PSCH-ReconfRqst-ExtIEs  NBAP-PROTOCOL-EXTENSION ::= {
	...
}

DL-Timeslot-InformationAddList-PSCH-ReconfRqst ::= SEQUENCE (SIZE (1.. maxNrOfDLTSs)) OF DL-Timeslot-InformationAddItem-PSCH-ReconfRqst

DL-Timeslot-InformationAddItem-PSCH-ReconfRqst ::= SEQUENCE {
	timeSlot								TimeSlot,
	midambleShiftAndBurstType				MidambleShiftAndBurstType,
	tFCI-Presence							TFCI-Presence,
	dL-Code-InformationAddList-PSCH-ReconfRqst				DL-Code-InformationAddList-PSCH-ReconfRqst,
	iE-Extensions							ProtocolExtensionContainer { { DL-Timeslot-InformationAddItem-PSCH-ReconfRqst-ExtIEs} }		OPTIONAL,
	...
}

DL-Timeslot-InformationAddItem-PSCH-ReconfRqst-ExtIEs NBAP-PROTOCOL-EXTENSION ::= {
	...
}

DL-Code-InformationAddList-PSCH-ReconfRqst ::= SEQUENCE (SIZE (1..maxNrOfPDSCHs)) OF DL-Code-InformationAddItem-PSCH-ReconfRqst

DL-Code-InformationAddItem-PSCH-ReconfRqst ::= SEQUENCE {
	pDSCH-ID								PDSCH-ID,
	tdd-ChannelisationCode					TDD-ChannelisationCode,
	iE-Extensions							ProtocolExtensionContainer { { DL-Code-InformationAddItem-PSCH-ReconfRqst-ExtIEs} }		OPTIONAL,
	...
}

DL-Code-InformationAddItem-PSCH-ReconfRqst-ExtIEs NBAP-PROTOCOL-EXTENSION ::= {
	...
}

PDSCH-AddInformation-LCR-AddItem-PSCH-ReconfRqst ::= SEQUENCE {
	repetitionPeriod						RepetitionPeriod,
	repetitionLength						RepetitionLength,
	tdd-PhysicalChannelOffset				TDD-PhysicalChannelOffset,
	dL-Timeslot-InformationAddList-LCR-PSCH-ReconfRqst				DL-Timeslot-InformationAddList-LCR-PSCH-ReconfRqst,
	iE-Extensions								ProtocolExtensionContainer { {PDSCH-AddInformation-LCR-AddItem-PSCH-ReconfRqst-ExtIEs} }		OPTIONAL,
	...
	}

PDSCH-AddInformation-LCR-AddItem-PSCH-ReconfRqst-ExtIEs  NBAP-PROTOCOL-EXTENSION ::= {
	...
}

DL-Timeslot-InformationAddList-LCR-PSCH-ReconfRqst ::= SEQUENCE (SIZE (1.. maxNrOfDLTSLCRs)) OF DL-Timeslot-InformationAddItem-LCR-PSCH-ReconfRqst

DL-Timeslot-InformationAddItem-LCR-PSCH-ReconfRqst ::= SEQUENCE {
	timeSlotLCR								TimeSlotLCR,
	midambleShiftLCR						MidambleShiftLCR,
	tFCI-Presence							TFCI-Presence,
	dL-Code-InformationAddList-LCR-PSCH-ReconfRqst				DL-Code-InformationAddList-LCR-PSCH-ReconfRqst,
	iE-Extensions							ProtocolExtensionContainer { { DL-Timeslot-InformationAddItem-LCR-PSCH-ReconfRqst-ExtIEs} }		OPTIONAL,
	...
}

DL-Timeslot-InformationAddItem-LCR-PSCH-ReconfRqst-ExtIEs NBAP-PROTOCOL-EXTENSION ::= {
	...
}

DL-Code-InformationAddList-LCR-PSCH-ReconfRqst ::= SEQUENCE (SIZE (1..maxNrOfPDSCHs)) OF DL-Code-InformationAddItem-LCR-PSCH-ReconfRqst

DL-Code-InformationAddItem-LCR-PSCH-ReconfRqst ::= SEQUENCE {
	pDSCH-ID								PDSCH-ID,
	tdd-ChannelisationCodeLCR				TDD-ChannelisationCodeLCR,
	iE-Extensions							ProtocolExtensionContainer { { DL-Code-InformationAddItem-LCR-PSCH-ReconfRqst-ExtIEs} }		OPTIONAL,
	...
}

DL-Code-InformationAddItem-LCR-PSCH-ReconfRqst-ExtIEs NBAP-PROTOCOL-EXTENSION ::= {
	...
}

PDSCHSets-ModifyList-PSCH-ReconfRqst ::= SEQUENCE (SIZE (1..maxNrOfPDSCHSets)) OF PDSCHSets-ModifyItem-PSCH-ReconfRqst

PDSCHSets-ModifyItem-PSCH-ReconfRqst	 ::= SEQUENCE {
	pDSCHSet-ID									PDSCHSet-ID,
	pDSCH-InformationList						PDSCH-Information-ModifyList-PSCH-ReconfRqst,
	iE-Extensions								ProtocolExtensionContainer { {PDSCHSets-ModifyItem-PSCH-ReconfRqst-ExtIEs} }		OPTIONAL,
	...
}

PDSCHSets-ModifyItem-PSCH-ReconfRqst-ExtIEs  NBAP-PROTOCOL-EXTENSION ::= {
	{ID id-PDSCH-ModifyInformation-LCR-PSCH-ReconfRqst 	CRITICALITY	reject		EXTENSION 	PDSCH-ModifyInformation-LCR-ModifyItem-PSCH-ReconfRqst			PRESENCE	optional},	-- Mandatory for 1.28Mcps TDD, Not Applicable to 3.84Mcps TDD
	...
}

PDSCH-Information-ModifyList-PSCH-ReconfRqst ::= ProtocolIE-Single-Container {{ PDSCH-Information-ModifyListIEs-PSCH-ReconfRqst }}

PDSCH-Information-ModifyListIEs-PSCH-ReconfRqst NBAP-PROTOCOL-IES ::= {
	{ID id-PDSCH-Information-ModifyListIE-PSCH-ReconfRqst 	CRITICALITY	reject		TYPE	PDSCH-Information-ModifyItem-PSCH-ReconfRqst			PRESENCE	optional}	-- Mandatory for 3.84Mcps TDD, Not Applicable to 1.28Mcps TDD
}

PDSCH-Information-ModifyItem-PSCH-ReconfRqst ::= SEQUENCE {
	repetitionPeriod						RepetitionPeriod					OPTIONAL,
	repetitionLength						RepetitionLength					OPTIONAL,
	tdd-PhysicalChannelOffset					TDD-PhysicalChannelOffset		OPTIONAL,
	dL-Timeslot-InformationModifyList-PSCH-ReconfRqst				DL-Timeslot-InformationModifyList-PSCH-ReconfRqst		OPTIONAL,
	iE-Extensions								ProtocolExtensionContainer { {PDSCH-Information-ModifyItem-PSCH-ReconfRqst-ExtIEs} }		OPTIONAL,
	...
	}

PDSCH-Information-ModifyItem-PSCH-ReconfRqst-ExtIEs  NBAP-PROTOCOL-EXTENSION ::= {
	...
}

DL-Timeslot-InformationModifyList-PSCH-ReconfRqst ::= SEQUENCE (SIZE (1.. maxNrOfDLTSs)) OF DL-Timeslot-InformationModifyItem-PSCH-ReconfRqst

DL-Timeslot-InformationModifyItem-PSCH-ReconfRqst ::= SEQUENCE {
	timeSlot								TimeSlot,
	midambleShiftAndBurstType				MidambleShiftAndBurstType	OPTIONAL,
	tFCI-Presence							TFCI-Presence	OPTIONAL,
	dL-Code-InformationModifyList-PSCH-ReconfRqst				DL-Code-InformationModifyList-PSCH-ReconfRqst		OPTIONAL,
	iE-Extensions							ProtocolExtensionContainer { { DL-Timeslot-InformationModifyItem-PSCH-ReconfRqst-ExtIEs} }		OPTIONAL,
	...
}

DL-Timeslot-InformationModifyItem-PSCH-ReconfRqst-ExtIEs NBAP-PROTOCOL-EXTENSION ::= {
	...
}

DL-Code-InformationModifyList-PSCH-ReconfRqst ::= SEQUENCE (SIZE (1..maxNrOfPDSCHs)) OF DL-Code-InformationModifyItem-PSCH-ReconfRqst

DL-Code-InformationModifyItem-PSCH-ReconfRqst ::= SEQUENCE {
	pDSCH-ID								PDSCH-ID,
	tdd-ChannelisationCode					TDD-ChannelisationCode,
	iE-Extensions							ProtocolExtensionContainer { { DL-Code-InformationModifyItem-PSCH-ReconfRqst-ExtIEs} }		OPTIONAL,
	...
}

DL-Code-InformationModifyItem-PSCH-ReconfRqst-ExtIEs NBAP-PROTOCOL-EXTENSION ::= {
	...
}

PDSCH-ModifyInformation-LCR-ModifyItem-PSCH-ReconfRqst ::= SEQUENCE {
	repetitionPeriod						RepetitionPeriod					OPTIONAL,
	repetitionLength						RepetitionLength					OPTIONAL,
	tdd-PhysicalChannelOffset					TDD-PhysicalChannelOffset		OPTIONAL,
	dL-Timeslot-LCR-InformationModifyList-PSCH-ReconfRqst				DL-Timeslot-LCR-InformationModifyList-PSCH-ReconfRqst		OPTIONAL,
	iE-Extensions								ProtocolExtensionContainer { {PDSCH-ModifyInformation-LCR-ModifyListIE-PSCH-ReconfRqst-ExtIEs} }		OPTIONAL,
	...
	}

PDSCH-ModifyInformation-LCR-ModifyListIE-PSCH-ReconfRqst-ExtIEs NBAP-PROTOCOL-EXTENSION ::= {
	...
}

DL-Timeslot-LCR-InformationModifyList-PSCH-ReconfRqst ::= SEQUENCE (SIZE (1.. maxNrOfDLTSLCRs)) OF DL-Timeslot-InformationModifyItem-PSCH-ReconfRqst

DL-Timeslot-LCR-InformationModifyItem-PSCH-ReconfRqst ::= SEQUENCE {
	timeSlotLCR								TimeSlotLCR,
	midambleShiftLCR						MidambleShiftLCR	OPTIONAL,
	tFCI-Presence							TFCI-Presence	OPTIONAL,
	dL-Code-LCR-InformationModifyList-PSCH-ReconfRqst				DL-Code-LCR-InformationModifyList-PSCH-ReconfRqst		OPTIONAL,
	iE-Extensions							ProtocolExtensionContainer { { DL-Timeslot-LCR-InformationModifyItem-PSCH-ReconfRqst-ExtIEs} }		OPTIONAL,
	...
}

DL-Timeslot-LCR-InformationModifyItem-PSCH-ReconfRqst-ExtIEs NBAP-PROTOCOL-EXTENSION ::= {
	...
}

DL-Code-LCR-InformationModifyList-PSCH-ReconfRqst ::= SEQUENCE (SIZE (1..maxNrOfPDSCHs)) OF DL-Code-InformationModifyItem-PSCH-ReconfRqst

DL-Code-LCR-InformationModifyItem-PSCH-ReconfRqst ::= SEQUENCE {
	pDSCH-ID								PDSCH-ID,
	tdd-ChannelisationCodeLCR					TDD-ChannelisationCodeLCR,
	iE-Extensions							ProtocolExtensionContainer { { DL-Code-LCR-InformationModifyItem-PSCH-ReconfRqst-ExtIEs} }		OPTIONAL,
	...
}

DL-Code-LCR-InformationModifyItem-PSCH-ReconfRqst-ExtIEs NBAP-PROTOCOL-EXTENSION ::= {
	...
}

PDSCHSets-DeleteList-PSCH-ReconfRqst ::= SEQUENCE (SIZE (1..maxNrOfPDSCHSets)) OF PDSCHSets-DeleteItem-PSCH-ReconfRqst

PDSCHSets-DeleteItem-PSCH-ReconfRqst	 ::= SEQUENCE {
	pDSCHSet-ID									PDSCHSet-ID,
	iE-Extensions								ProtocolExtensionContainer { {PDSCHSets-DeleteItem-PSCH-ReconfRqst-ExtIEs} }		OPTIONAL,
	...
}

PDSCHSets-DeleteItem-PSCH-ReconfRqst-ExtIEs  NBAP-PROTOCOL-EXTENSION ::= {
	...
}

PUSCHSets-AddList-PSCH-ReconfRqst ::= SEQUENCE (SIZE (1..maxNrOfPUSCHSets)) OF PUSCHSets-AddItem-PSCH-ReconfRqst

PUSCHSets-AddItem-PSCH-ReconfRqst	 ::= SEQUENCE {
	pUSCHSet-ID									PUSCHSet-ID,
	pUSCH-InformationList						PUSCH-Information-AddList-PSCH-ReconfRqst 	OPTIONAL,
	-- Mandatory for 3.84Mcps TDD, Not Applicable to 1.28Mcps TDD
	iE-Extensions								ProtocolExtensionContainer { {PUSCHSets-AddItem-PSCH-ReconfRqst-ExtIEs} }		OPTIONAL,
	...
}

PUSCHSets-AddItem-PSCH-ReconfRqst-ExtIEs  NBAP-PROTOCOL-EXTENSION ::= {
	{ID id-PUSCH-AddInformation-LCR-PSCH-ReconfRqst 	CRITICALITY	reject		EXTENSION 	PUSCH-AddInformation-LCR-AddItem-PSCH-ReconfRqst			PRESENCE	optional},	-- Mandatory for 1.28Mcps TDD, Not Applicable to 3.84Mcps TDD
	...
}

PUSCH-Information-AddList-PSCH-ReconfRqst ::=  ProtocolIE-Single-Container {{ PUSCH-Information-AddListIEs-PSCH-ReconfRqst }}

PUSCH-Information-AddListIEs-PSCH-ReconfRqst NBAP-PROTOCOL-IES ::= {
	{ID id-PUSCH-Information-AddListIE-PSCH-ReconfRqst 	CRITICALITY	reject		TYPE	PUSCH-Information-AddItem-PSCH-ReconfRqst			PRESENCE	mandatory}
}

PUSCH-Information-AddItem-PSCH-ReconfRqst ::= SEQUENCE {
	repetitionPeriod						RepetitionPeriod,
	repetitionLength						RepetitionLength,
	tdd-PhysicalChannelOffset				TDD-PhysicalChannelOffset,
	uL-Timeslot-InformationAddList-PSCH-ReconfRqst				UL-Timeslot-InformationAddList-PSCH-ReconfRqst,
	iE-Extensions								ProtocolExtensionContainer { {PUSCH-Information-AddItem-PSCH-ReconfRqst-ExtIEs} }		OPTIONAL,
	...
	}

PUSCH-Information-AddItem-PSCH-ReconfRqst-ExtIEs  NBAP-PROTOCOL-EXTENSION ::= {
	...
}

UL-Timeslot-InformationAddList-PSCH-ReconfRqst ::= SEQUENCE (SIZE (1..maxNrOfULTSs)) OF UL-Timeslot-InformationAddItem-PSCH-ReconfRqst

UL-Timeslot-InformationAddItem-PSCH-ReconfRqst ::= SEQUENCE {
	timeSlot								TimeSlot,
	midambleShiftAndBurstType				MidambleShiftAndBurstType,
	tFCI-Presence							TFCI-Presence,
	uL-Code-InformationAddList-PSCH-ReconfRqst				UL-Code-InformationAddList-PSCH-ReconfRqst,
	iE-Extensions							ProtocolExtensionContainer { { UL-Timeslot-InformationAddItem-PSCH-ReconfRqst-ExtIEs} }		OPTIONAL,
	...
}

UL-Timeslot-InformationAddItem-PSCH-ReconfRqst-ExtIEs NBAP-PROTOCOL-EXTENSION ::= {
	...
}

UL-Code-InformationAddList-PSCH-ReconfRqst ::= SEQUENCE (SIZE (1..maxNrOfPUSCHs)) OF UL-Code-InformationAddItem-PSCH-ReconfRqst

UL-Code-InformationAddItem-PSCH-ReconfRqst ::= SEQUENCE {
	pUSCH-ID								PUSCH-ID,
	tdd-ChannelisationCode					TDD-ChannelisationCode,
	iE-Extensions							ProtocolExtensionContainer { { UL-Code-InformationAddItem-PSCH-ReconfRqst-ExtIEs} }		OPTIONAL,
	...
}

UL-Code-InformationAddItem-PSCH-ReconfRqst-ExtIEs NBAP-PROTOCOL-EXTENSION ::= {
	...
}

PUSCH-AddInformation-LCR-AddItem-PSCH-ReconfRqst ::= SEQUENCE {
	repetitionPeriod						RepetitionPeriod,
	repetitionLength						RepetitionLength,
	tdd-PhysicalChannelOffset				TDD-PhysicalChannelOffset,
	uL-Timeslot-InformationAddList-LCR-PSCH-ReconfRqst				UL-Timeslot-InformationAddList-LCR-PSCH-ReconfRqst,
	iE-Extensions								ProtocolExtensionContainer { {PUSCH-AddInformation-LCR-AddItem-PSCH-ReconfRqst-ExtIEs} }		OPTIONAL,
	...
	}

PUSCH-AddInformation-LCR-AddItem-PSCH-ReconfRqst-ExtIEs  NBAP-PROTOCOL-EXTENSION ::= {
	...
}

UL-Timeslot-InformationAddList-LCR-PSCH-ReconfRqst ::= SEQUENCE (SIZE (1.. maxNrOfULTSLCRs)) OF UL-Timeslot-InformationAddItem-LCR-PSCH-ReconfRqst

UL-Timeslot-InformationAddItem-LCR-PSCH-ReconfRqst ::= SEQUENCE {
	timeSlotLCR								TimeSlotLCR,
	midambleShiftLCR						MidambleShiftLCR,
	tFCI-Presence							TFCI-Presence,
	uL-Code-InformationAddList-LCR-PSCH-ReconfRqst				UL-Code-InformationAddList-LCR-PSCH-ReconfRqst,
	iE-Extensions							ProtocolExtensionContainer { { UL-Timeslot-InformationAddItem-LCR-PSCH-ReconfRqst-ExtIEs} }		OPTIONAL,
	...
}

UL-Timeslot-InformationAddItem-LCR-PSCH-ReconfRqst-ExtIEs NBAP-PROTOCOL-EXTENSION ::= {
	...
}

UL-Code-InformationAddList-LCR-PSCH-ReconfRqst ::= SEQUENCE (SIZE (1..maxNrOfPUSCHs)) OF UL-Code-InformationAddItem-LCR-PSCH-ReconfRqst

UL-Code-InformationAddItem-LCR-PSCH-ReconfRqst ::= SEQUENCE {
	pUSCH-ID								PUSCH-ID,
	tdd-ChannelisationCodeLCR				TDD-ChannelisationCodeLCR,
	iE-Extensions							ProtocolExtensionContainer { { UL-Code-InformationAddItem-LCR-PSCH-ReconfRqst-ExtIEs} }		OPTIONAL,
	...
}

UL-Code-InformationAddItem-LCR-PSCH-ReconfRqst-ExtIEs NBAP-PROTOCOL-EXTENSION ::= {
	...
}

PUSCHSets-ModifyList-PSCH-ReconfRqst ::= SEQUENCE (SIZE (1..maxNrOfPUSCHSets)) OF PUSCHSets-ModifyItem-PSCH-ReconfRqst

PUSCHSets-ModifyItem-PSCH-ReconfRqst	 ::= SEQUENCE {
	pUSCHSet-ID									PUSCHSet-ID,
	pUSCH-InformationList						PUSCH-Information-ModifyList-PSCH-ReconfRqst 	OPTIONAL,
	-- Applicable to 3.84Mcps TDD only
	iE-Extensions								ProtocolExtensionContainer { {PUSCHSets-ModifyItem-PSCH-ReconfRqst-ExtIEs} }		OPTIONAL,
	...
}

PUSCHSets-ModifyItem-PSCH-ReconfRqst-ExtIEs  NBAP-PROTOCOL-EXTENSION ::= {
	{ID id-PUSCH-ModifyInformation-LCR-PSCH-ReconfRqst 	CRITICALITY	reject		EXTENSION 	PUSCH-ModifyInformation-LCR-ModifyItem-PSCH-ReconfRqst			PRESENCE	optional},	-- Applicable to 1.28Mcps TDD only
	...
}

PUSCH-Information-ModifyList-PSCH-ReconfRqst ::= ProtocolIE-Single-Container {{ PUSCH-Information-ModifyListIEs-PSCH-ReconfRqst }}	

PUSCH-Information-ModifyListIEs-PSCH-ReconfRqst NBAP-PROTOCOL-IES ::= {
	{ID id-PUSCH-Information-ModifyListIE-PSCH-ReconfRqst 	CRITICALITY	reject		TYPE	PUSCH-Information-ModifyItem-PSCH-ReconfRqst			PRESENCE	mandatory}
}

PUSCH-Information-ModifyItem-PSCH-ReconfRqst ::= SEQUENCE {
	repetitionPeriod						RepetitionPeriod					OPTIONAL,
	repetitionLength						RepetitionLength					OPTIONAL,
	tdd-PhysicalChannelOffset				TDD-PhysicalChannelOffset			OPTIONAL,
	uL-Timeslot-InformationModifyList-PSCH-ReconfRqst				UL-Timeslot-InformationModifyList-PSCH-ReconfRqst		OPTIONAL,
	iE-Extensions								ProtocolExtensionContainer { {PUSCH-Information-ModifyItem-PSCH-ReconfRqst-ExtIEs} }		OPTIONAL,
		...
	}

PUSCH-Information-ModifyItem-PSCH-ReconfRqst-ExtIEs  NBAP-PROTOCOL-EXTENSION ::= {
	...
}

UL-Timeslot-InformationModifyList-PSCH-ReconfRqst ::= SEQUENCE (SIZE (1..maxNrOfULTSs)) OF UL-Timeslot-InformationModifyItem-PSCH-ReconfRqst

UL-Timeslot-InformationModifyItem-PSCH-ReconfRqst ::= SEQUENCE {
	timeSlot								TimeSlot,
	midambleShiftAndBurstType				MidambleShiftAndBurstType	OPTIONAL,
	tFCI-Presence							TFCI-Presence	OPTIONAL,
	uL-Code-InformationModifyList-PSCH-ReconfRqst				UL-Code-InformationModifyList-PSCH-ReconfRqst		OPTIONAL,
	iE-Extensions							ProtocolExtensionContainer { { UL-Timeslot-InformationModifyItem-PSCH-ReconfRqst-ExtIEs} }		OPTIONAL,
	...
}

UL-Timeslot-InformationModifyItem-PSCH-ReconfRqst-ExtIEs NBAP-PROTOCOL-EXTENSION ::= {
	...
}

UL-Code-InformationModifyList-PSCH-ReconfRqst ::= SEQUENCE (SIZE (1..maxNrOfPUSCHs)) OF UL-Code-InformationModifyItem-PSCH-ReconfRqst

UL-Code-InformationModifyItem-PSCH-ReconfRqst ::= SEQUENCE {
	pUSCH-ID								PUSCH-ID,
	tdd-ChannelisationCode					TDD-ChannelisationCode,
	iE-Extensions							ProtocolExtensionContainer { { UL-Code-InformationModifyItem-PSCH-ReconfRqst-ExtIEs} }		OPTIONAL,
	...
}

UL-Code-InformationModifyItem-PSCH-ReconfRqst-ExtIEs NBAP-PROTOCOL-EXTENSION ::= {
	...
}

PUSCH-ModifyInformation-LCR-ModifyItem-PSCH-ReconfRqst ::= SEQUENCE {
	repetitionPeriod						RepetitionPeriod		OPTIONAL,
	repetitionLength						RepetitionLength		OPTIONAL,
	tdd-PhysicalChannelOffset				TDD-PhysicalChannelOffset	OPTIONAL,
	uL-Timeslot-InformationModifyList-LCR-PSCH-ReconfRqst				UL-Timeslot-LCR-InformationModifyList-PSCH-ReconfRqst		OPTIONAL,
	iE-Extensions								ProtocolExtensionContainer { {PUSCH-ModifyInformation-LCR-ModifyItem-PSCH-ReconfRqst-ExtIEs} }		OPTIONAL,
		...
	}

PUSCH-ModifyInformation-LCR-ModifyItem-PSCH-ReconfRqst-ExtIEs  NBAP-PROTOCOL-EXTENSION ::= {
	...
}

UL-Timeslot-LCR-InformationModifyList-PSCH-ReconfRqst ::= SEQUENCE (SIZE (1..maxNrOfULTSLCRs)) OF UL-Timeslot-InformationModifyItem-PSCH-ReconfRqst

UL-Timeslot-LCR-InformationModifyItem-PSCH-ReconfRqst ::= SEQUENCE {
	timeSlotLCR								TimeSlotLCR,
	midambleShiftLCR						MidambleShiftLCR 	OPTIONAL,
	tFCI-Presence							TFCI-Presence		OPTIONAL,
	uL-Code-InformationModifyList-PSCH-ReconfRqst				UL-Code-InformationModifyList-PSCH-ReconfRqst		OPTIONAL,
	iE-Extensions							ProtocolExtensionContainer { { UL-Timeslot-LCR-InformationModifyItem-PSCH-ReconfRqst-ExtIEs} }		OPTIONAL,
	...
}

UL-Timeslot-LCR-InformationModifyItem-PSCH-ReconfRqst-ExtIEs NBAP-PROTOCOL-EXTENSION ::= {
	...
}

UL-Code-LCR-InformationModifyList-PSCH-ReconfRqst ::= SEQUENCE (SIZE (1..maxNrOfPUSCHs)) OF UL-Code-InformationModifyItem-PSCH-ReconfRqst

UL-Code-LCR-InformationModifyItem-PSCH-ReconfRqst ::= SEQUENCE {
	pUSCH-ID								PUSCH-ID,
	tdd-ChannelisationCodeLCR					TDD-ChannelisationCodeLCR,
	iE-Extensions							ProtocolExtensionContainer { { UL-Code-LCR-InformationModifyItem-PSCH-ReconfRqst-ExtIEs} }		OPTIONAL,
	...
}

UL-Code-LCR-InformationModifyItem-PSCH-ReconfRqst-ExtIEs NBAP-PROTOCOL-EXTENSION ::= {
	...
}

PUSCHSets-DeleteList-PSCH-ReconfRqst ::= SEQUENCE (SIZE (1..maxNrOfPUSCHSets)) OF PUSCHSets-DeleteItem-PSCH-ReconfRqst

PUSCHSets-DeleteItem-PSCH-ReconfRqst	 ::= SEQUENCE {
	pUSCHSet-ID									PUSCHSet-ID,
	iE-Extensions								ProtocolExtensionContainer { {PUSCHSets-DeleteItem-PSCH-ReconfRqst-ExtIEs} }		OPTIONAL,
	...
}

PUSCHSets-DeleteItem-PSCH-ReconfRqst-ExtIEs  NBAP-PROTOCOL-EXTENSION ::= {
	...
}

HS-PDSCH-TDD-Information-PSCH-ReconfRqst ::= CHOICE {
	replace					HS-PDSCH-TDD-TSInfo-PSCH-ReconfRqst,
	remove					NULL,
	...
}

HS-PDSCH-TDD-TSInfo-PSCH-ReconfRqst ::= SEQUENCE {
	dL-HS-PDSCH-Timeslot-Information-PSCH-ReconfRqst					DL-HS-PDSCH-Timeslot-Information-PSCH-ReconfRqst		OPTIONAL,
	dL-HS-PDSCH-Timeslot-Information-LCR-PSCH-ReconfRqst				DL-HS-PDSCH-Timeslot-Information-LCR-PSCH-ReconfRqst		OPTIONAL,
	iE-Extensions								ProtocolExtensionContainer { { HS-PDSCH-TDD-TSInfo-PSCH-ReconfRqst-ExtIEs} }		OPTIONAL,
		...
	}

HS-PDSCH-TDD-TSInfo-PSCH-ReconfRqst-ExtIEs  NBAP-PROTOCOL-EXTENSION ::= {
	...
}

DL-HS-PDSCH-Timeslot-Information-PSCH-ReconfRqst ::= SEQUENCE (SIZE (1..maxNrOfDLTSs)) OF DL-HS-PDSCH-Timeslot-InformationItem-PSCH-ReconfRqst

DL-HS-PDSCH-Timeslot-InformationItem-PSCH-ReconfRqst::= SEQUENCE {
	timeSlot								TimeSlot,
	midambleShiftAndBurstType				MidambleShiftAndBurstType,
	iE-Extensions							ProtocolExtensionContainer { { DL-HS-PDSCH-Timeslot-InformationItem-PSCH-ReconfRqst-ExtIEs} }		OPTIONAL,
	...
}

DL-HS-PDSCH-Timeslot-InformationItem-PSCH-ReconfRqst-ExtIEs NBAP-PROTOCOL-EXTENSION ::= {
	...
}

DL-HS-PDSCH-Timeslot-Information-LCR-PSCH-ReconfRqst ::= SEQUENCE (SIZE (1..maxNrOfDLTSLCRs)) OF DL-HS-PDSCH-Timeslot-InformationItem-LCR-PSCH-ReconfRqst

DL-HS-PDSCH-Timeslot-InformationItem-LCR-PSCH-ReconfRqst::= SEQUENCE {
	timeSlot								TimeSlotLCR,
	midambleShiftAndBurstType				MidambleShiftLCR,
	iE-Extensions							ProtocolExtensionContainer { { DL-HS-PDSCH-Timeslot-InformationItem-LCR-PSCH-ReconfRqst-ExtIEs} }		OPTIONAL,
	...
}

DL-HS-PDSCH-Timeslot-InformationItem-LCR-PSCH-ReconfRqst-ExtIEs NBAP-PROTOCOL-EXTENSION ::= {
	...
}

Add-To-HS-SCCH-Resource-Pool-PSCH-ReconfRqst::= SEQUENCE {
	hS-SCCH-Information-PSCH-ReconfRqst		HS-SCCH-Information-PSCH-ReconfRqst		OPTIONAL,
	hS-SCCH-Information-LCR-PSCH-ReconfRqst	HS-SCCH-Information-PSCH-ReconfRqst		OPTIONAL,
	iE-Extensions							ProtocolExtensionContainer { { Add-To-HS-SCCH-Resource-Pool-PSCH-ReconfRqst-ExtIEs} }		OPTIONAL,
	...
}

Add-To-HS-SCCH-Resource-Pool-PSCH-ReconfRqst-ExtIEs NBAP-PROTOCOL-EXTENSION ::= {
	...
}

HS-SCCH-Information-PSCH-ReconfRqst::= SEQUENCE (SIZE (1..maxNrOfHSSCCHs)) OF HS-SCCH-InformationItem-PSCH-ReconfRqst

HS-SCCH-InformationItem-PSCH-ReconfRqst	 ::= SEQUENCE {
	hS-SCCH-ID								HS-SCCH-ID,
	timeSlot								TimeSlot,
	midambleShiftAndBurstType				MidambleShiftAndBurstType,
	tdd-ChannelisationCode					TDD-ChannelisationCode,
	hS-SCCH-MaxPower						DL-Power,
	hS-SICH-Information						HS-SICH-Information-PSCH-ReconfRqst,
	iE-Extensions							ProtocolExtensionContainer { { HS-SCCH-InformationItem-PSCH-ReconfRqst-ExtIEs} }		OPTIONAL,
	...
}

HS-SCCH-InformationItem-PSCH-ReconfRqst-ExtIEs  NBAP-PROTOCOL-EXTENSION ::= {
	...
}

HS-SICH-Information-PSCH-ReconfRqst	 ::= SEQUENCE {
	timeSlot								TimeSlot,
	midambleShiftAndBurstType				MidambleShiftAndBurstType,
	tdd-ChannelisationCode					TDD-ChannelisationCode,
	iE-Extensions							ProtocolExtensionContainer { { HS-SICH-Information-PSCH-ReconfRqst-ExtIEs} }		OPTIONAL,
	...
}

HS-SICH-Information-PSCH-ReconfRqst-ExtIEs  NBAP-PROTOCOL-EXTENSION ::= {
	...
}

HS-SCCH-Information-LCR-PSCH-ReconfRqst::= SEQUENCE (SIZE (1..maxNrOfHSSCCHs)) OF HS-SCCH-InformationItem-LCR-PSCH-ReconfRqst

HS-SCCH-InformationItem-LCR-PSCH-ReconfRqst	 ::= SEQUENCE {
	hS-SCCH-ID								HS-SCCH-ID,
	timeSlotLCR								TimeSlotLCR,
	midambleShiftLCR						MidambleShiftLCR,
	first-TDD-ChannelisationCode			TDD-ChannelisationCodeLCR,
	second-TDD-ChannelisationCode			TDD-ChannelisationCodeLCR,
	hS-SCCH-MaxPower						DL-Power,
	hS-SICH-Information-LCR					HS-SICH-Information-LCR-PSCH-ReconfRqst,
	iE-Extensions							ProtocolExtensionContainer { { HS-SCCH-InformationItem-LCR-PSCH-ReconfRqst-ExtIEs} }		OPTIONAL,
	...
}

HS-SCCH-InformationItem-LCR-PSCH-ReconfRqst-ExtIEs  NBAP-PROTOCOL-EXTENSION ::= {
	...
}

HS-SICH-Information-LCR-PSCH-ReconfRqst	 ::= SEQUENCE {
	timeSlotLCR								TimeSlotLCR,
	midambleShiftLCR						MidambleShiftLCR,
	tdd-ChannelisationCodeLCR				TDD-ChannelisationCodeLCR,
	iE-Extensions							ProtocolExtensionContainer { { HS-SICH-Information-LCR-PSCH-ReconfRqst-ExtIEs} }		OPTIONAL,
	...
}

HS-SICH-Information-LCR-PSCH-ReconfRqst-ExtIEs  NBAP-PROTOCOL-EXTENSION ::= {
	...
}

Modify-HS-SCCH-Resource-Pool-PSCH-ReconfRqst::= SEQUENCE {
	hS-SCCH-InformationModify-PSCH-ReconfRqst		HS-SCCH-InformationModify-PSCH-ReconfRqst	OPTIONAL,
	hS-SCCH-InformationModify-LCR-PSCH-ReconfRqst	HS-SCCH-InformationModify-PSCH-ReconfRqst	OPTIONAL,
	iE-Extensions									ProtocolExtensionContainer { { Modify-HS-SCCH-Resource-Pool-PSCH-ReconfRqst-ExtIEs} }		OPTIONAL,
	...
}

Modify-HS-SCCH-Resource-Pool-PSCH-ReconfRqst-ExtIEs NBAP-PROTOCOL-EXTENSION ::= {
	...
}

HS-SCCH-InformationModify-PSCH-ReconfRqst::= SEQUENCE (SIZE (1..maxNrOfHSSCCHs)) OF HS-SCCH-InformationModifyItem-PSCH-ReconfRqst

HS-SCCH-InformationModifyItem-PSCH-ReconfRqst	 ::= SEQUENCE {
	hS-SCCH-ID								HS-SCCH-ID,
	timeSlot								TimeSlot 	OPTIONAL,
	midambleShiftAndBurstType				MidambleShiftAndBurstType 	OPTIONAL,
	tdd-ChannelisationCode					TDD-ChannelisationCode 	OPTIONAL,
	hS-SCCH-MaxPower						DL-Power 	OPTIONAL,
	hS-SICH-Information						HS-SICH-Information-PSCH-ReconfRqst 	OPTIONAL,
	iE-Extensions							ProtocolExtensionContainer { { HS-SCCH-InformationModifyItem-PSCH-ReconfRqst-ExtIEs} }		OPTIONAL,
	...
}

HS-SCCH-InformationModifyItem-PSCH-ReconfRqst-ExtIEs  NBAP-PROTOCOL-EXTENSION ::= {
	...
}

HS-SICH-InformationModify-PSCH-ReconfRqst	 ::= SEQUENCE {
	timeSlot								TimeSlot 	OPTIONAL,
	midambleShiftAndBurstType				MidambleShiftAndBurstType 	OPTIONAL,
	tdd-ChannelisationCode					TDD-ChannelisationCode 	OPTIONAL,
	iE-Extensions							ProtocolExtensionContainer { { HS-SICH-InformationModify-PSCH-ReconfRqst-ExtIEs} }		OPTIONAL,
	...
}

HS-SICH-InformationModify-PSCH-ReconfRqst-ExtIEs  NBAP-PROTOCOL-EXTENSION ::= {
	...
}

HS-SCCH-InformationModify-LCR-PSCH-ReconfRqst::= SEQUENCE (SIZE (1..maxNrOfHSSCCHs)) OF HS-SCCH-InformationModifyItem-LCR-PSCH-ReconfRqst

HS-SCCH-InformationModifyItem-LCR-PSCH-ReconfRqst	 ::= SEQUENCE {
	hS-SCCH-ID								HS-SCCH-ID,
	timeSlotLCR								TimeSlotLCR 	OPTIONAL,
	midambleShiftLCR						MidambleShiftLCR 	OPTIONAL,
	first-TDD-ChannelisationCode			TDD-ChannelisationCodeLCR 	OPTIONAL,
	second-TDD-ChannelisationCode			TDD-ChannelisationCodeLCR	OPTIONAL,
	hS-SCCH-MaxPower						DL-Power 	OPTIONAL,
	hS-SICH-Information-LCR					HS-SICH-Information-LCR-PSCH-ReconfRqst 	OPTIONAL,
	iE-Extensions							ProtocolExtensionContainer { { HS-SCCH-InformationModifyItem-LCR-PSCH-ReconfRqst-ExtIEs} }		OPTIONAL,
	...
}

HS-SCCH-InformationModifyItem-LCR-PSCH-ReconfRqst-ExtIEs  NBAP-PROTOCOL-EXTENSION ::= {
	...
}

HS-SICH-InformationModify-LCR-PSCH-ReconfRqst	 ::= SEQUENCE {
	timeSlotLCR								TimeSlotLCR 	OPTIONAL,
	midambleShiftLCR						MidambleShiftLCR 	OPTIONAL,
	tdd-ChannelisationCodeLCR				TDD-ChannelisationCodeLCR 	OPTIONAL,
	iE-Extensions							ProtocolExtensionContainer { { HS-SICH-InformationModify-LCR-PSCH-ReconfRqst-ExtIEs} }		OPTIONAL,
	...
}

HS-SICH-InformationModify-LCR-PSCH-ReconfRqst-ExtIEs  NBAP-PROTOCOL-EXTENSION ::= {
	...
}

Delete-From-HS-SCCH-Resource-Pool-PSCH-ReconfRqst ::= SEQUENCE (SIZE (1..maxNrOfHSSCCHs)) OF Delete-From-HS-SCCH-Resource-PoolItem-PSCH-ReconfRqst

Delete-From-HS-SCCH-Resource-PoolItem-PSCH-ReconfRqst	 ::= SEQUENCE {
	hS-SCCH-ID								HS-SCCH-ID,
	iE-Extensions								ProtocolExtensionContainer { { Delete-From-HS-SCCH-Resource-PoolItem-PSCH-ReconfRqst-ExtIEs} }		OPTIONAL,
	...
}

Delete-From-HS-SCCH-Resource-PoolItem-PSCH-ReconfRqst-ExtIEs  NBAP-PROTOCOL-EXTENSION ::= {
	...
}

-- **************************************************************
--
-- PHYSICAL SHARED CHANNEL RECONFIGURATION RESPONSE
--
-- **************************************************************

PhysicalSharedChannelReconfigurationResponse ::= SEQUENCE {
	protocolIEs			ProtocolIE-Container  {{PhysicalSharedChannelReconfigurationResponse-IEs}},
	protocolExtensions	ProtocolExtensionContainer {{PhysicalSharedChannelReconfigurationResponse-Extensions}}                   OPTIONAL,
	...
}

PhysicalSharedChannelReconfigurationResponse-IEs NBAP-PROTOCOL-IES ::= {
	{ ID	id-CriticalityDiagnostics		CRITICALITY		ignore		TYPE		CriticalityDiagnostics		PRESENCE	optional	},
	...
}

PhysicalSharedChannelReconfigurationResponse-Extensions NBAP-PROTOCOL-EXTENSION ::= {
	...
}


-- **************************************************************
--
-- PHYSICAL SHARED CHANNEL RECONFIGURATION FAILURE
--
-- **************************************************************

PhysicalSharedChannelReconfigurationFailure ::= SEQUENCE {
	protocolIEs			ProtocolIE-Container  {{PhysicalSharedChannelReconfigurationFailure-IEs}},
	protocolExtensions	ProtocolExtensionContainer {{PhysicalSharedChannelReconfigurationFailure-Extensions}}                   OPTIONAL,
	...
}

PhysicalSharedChannelReconfigurationFailure-IEs NBAP-PROTOCOL-IES ::= {
	{ ID    id-CauseLevel-PSCH-ReconfFailure		CRITICALITY ignore	TYPE CauseLevel-PSCH-ReconfFailure	 PRESENCE mandatory }|
	{ ID	id-CriticalityDiagnostics		CRITICALITY ignore		TYPE	CriticalityDiagnostics	PRESENCE	optional	},
	...
}

PhysicalSharedChannelReconfigurationFailure-Extensions NBAP-PROTOCOL-EXTENSION ::= {
	...
}

CauseLevel-PSCH-ReconfFailure ::= CHOICE {
	generalCause			GeneralCauseList-PSCH-ReconfFailure,
	setSpecificCause		SetSpecificCauseList-PSCH-ReconfFailureTDD,
	...
}

GeneralCauseList-PSCH-ReconfFailure ::= SEQUENCE {
	cause						Cause,
	iE-Extensions				ProtocolExtensionContainer { { GeneralCauseItem-PSCH-ReconfFailure-ExtIEs} }		OPTIONAL,
	...
}

GeneralCauseItem-PSCH-ReconfFailure-ExtIEs NBAP-PROTOCOL-EXTENSION ::= {
	...
}

SetSpecificCauseList-PSCH-ReconfFailureTDD ::= SEQUENCE {
	unsuccessful-PDSCHSetList-PSCH-ReconfFailureTDD	Unsuccessful-PDSCHSetList-PSCH-ReconfFailureTDD		OPTIONAL,
	unsuccessful-PUSCHSetList-PSCH-ReconfFailureTDD	Unsuccessful-PUSCHSetList-PSCH-ReconfFailureTDD		OPTIONAL,
	iE-Extensions									ProtocolExtensionContainer { { SetSpecificCauseItem-PSCH-ReconfFailureTDD-ExtIEs} }		OPTIONAL,
	...
}

SetSpecificCauseItem-PSCH-ReconfFailureTDD-ExtIEs NBAP-PROTOCOL-EXTENSION ::= {
	...
}

Unsuccessful-PDSCHSetList-PSCH-ReconfFailureTDD ::= SEQUENCE (SIZE (0.. maxNrOfPDSCHSets)) OF ProtocolIE-Single-Container {{ Unsuccessful-PDSCHSetItemIE-PSCH-ReconfFailureTDD }}

Unsuccessful-PDSCHSetItemIE-PSCH-ReconfFailureTDD NBAP-PROTOCOL-IES ::= {
	{ ID	id-Unsuccessful-PDSCHSetItem-PSCH-ReconfFailureTDD	CRITICALITY ignore	TYPE Unsuccessful-PDSCHSetItem-PSCH-ReconfFailureTDD	PRESENCE mandatory}
}

Unsuccessful-PDSCHSetItem-PSCH-ReconfFailureTDD ::= SEQUENCE {
	pDSCHSet-ID				PDSCHSet-ID,
	cause					Cause,
	iE-Extensions			ProtocolExtensionContainer { {Unsuccessful-PDSCHSetItem-PSCH-ReconfFailureTDD-ExtIEs} }		OPTIONAL,
	...
}

Unsuccessful-PDSCHSetItem-PSCH-ReconfFailureTDD-ExtIEs NBAP-PROTOCOL-EXTENSION ::= {
	...
}

Unsuccessful-PUSCHSetList-PSCH-ReconfFailureTDD ::= SEQUENCE (SIZE (0.. maxNrOfPUSCHSets)) OF ProtocolIE-Single-Container {{ Unsuccessful-PUSCHSetItemIE-PSCH-ReconfFailureTDD }}

Unsuccessful-PUSCHSetItemIE-PSCH-ReconfFailureTDD NBAP-PROTOCOL-IES ::= {
	{ ID	id-Unsuccessful-PUSCHSetItem-PSCH-ReconfFailureTDD	CRITICALITY ignore	TYPE Unsuccessful-PUSCHSetItem-PSCH-ReconfFailureTDD	PRESENCE mandatory}
}

Unsuccessful-PUSCHSetItem-PSCH-ReconfFailureTDD ::= SEQUENCE {
	pUSCHSet-ID				PUSCHSet-ID,
	cause					Cause,
	iE-Extensions			ProtocolExtensionContainer { {Unsuccessful-PUSCHSetItem-PSCH-ReconfFailureTDD-ExtIEs} }		OPTIONAL,
	...
}

Unsuccessful-PUSCHSetItem-PSCH-ReconfFailureTDD-ExtIEs NBAP-PROTOCOL-EXTENSION ::= {
	...
}

-- **************************************************************
--
-- RESET REQUEST
--
-- **************************************************************

ResetRequest ::= SEQUENCE {
	protocolIEs				ProtocolIE-Container	{{ResetRequest-IEs}},
	protocolExtensions		ProtocolExtensionContainer	{{ResetRequest-Extensions}}		OPTIONAL,
	...
}

ResetRequest-IEs NBAP-PROTOCOL-IES ::= {
	{ID	id-ResetIndicator		CRITICALITY	ignore		TYPE 	ResetIndicator		PRESENCE 	mandatory},
	...
}

ResetRequest-Extensions NBAP-PROTOCOL-EXTENSION ::= {
	...
}

ResetIndicator ::= CHOICE {
	communicationContext			CommunicationContextList-Reset,
	communicationControlPort		CommunicationControlPortList-Reset,
	nodeB							NULL,
	...
}

CommunicationContextList-Reset ::= SEQUENCE {
	communicationContextInfoList-Reset		CommunicationContextInfoList-Reset,
	iE-Extensions							ProtocolExtensionContainer  { {CommunicationContextItem-Reset-ExtIEs} }		OPTIONAL,
	...
}

CommunicationContextItem-Reset-ExtIEs NBAP-PROTOCOL-EXTENSION ::= {
	...
}

CommunicationContextInfoList-Reset ::= SEQUENCE (SIZE (1.. maxCommunicationContext))	OF ProtocolIE-Single-Container {{ CommunicationContextInfoItemIE-Reset }}

CommunicationContextInfoItemIE-Reset NBAP-PROTOCOL-IES ::= {
	{ID id-CommunicationContextInfoItem-Reset		CRITICALITY reject		TYPE CommunicationContextInfoItem-Reset		PRESENCE mandatory}
}

CommunicationContextInfoItem-Reset ::= SEQUENCE {
	communicationContextType-Reset			CommunicationContextType-Reset,
	iE-Extensions							ProtocolExtensionContainer  { { CommunicationContextInfoItem-Reset-ExtIEs} }		OPTIONAL,
	...
}

CommunicationContextInfoItem-Reset-ExtIEs NBAP-PROTOCOL-EXTENSION ::= {
	...
}

CommunicationContextType-Reset ::= CHOICE {
	cRNC-CommunicationContextID				CRNC-CommunicationContextID,
	nodeB-CommunicationContextID			NodeB-CommunicationContextID,
	...
}

CommunicationControlPortList-Reset ::= SEQUENCE {
	communicationControlPortInfoList-Reset		CommunicationControlPortInfoList-Reset,
	iE-Extensions								ProtocolExtensionContainer  { {CommunicationControlPortItem-Reset-ExtIEs} }		OPTIONAL,
	...
}

CommunicationControlPortItem-Reset-ExtIEs NBAP-PROTOCOL-EXTENSION ::= {
	...
}

CommunicationControlPortInfoList-Reset ::= SEQUENCE (SIZE (1.. maxCCPinNodeB))	OF ProtocolIE-Single-Container {{CommunicationControlPortInfoItemIE-Reset }}

CommunicationControlPortInfoItemIE-Reset NBAP-PROTOCOL-IES ::= {
	{ID id-CommunicationControlPortInfoItem-Reset		CRITICALITY reject		TYPE CommunicationControlPortInfoItem-Reset		PRESENCE mandatory}
}

CommunicationControlPortInfoItem-Reset ::= SEQUENCE {
	communicationControlPortID			CommunicationControlPortID,
	iE-Extensions						ProtocolExtensionContainer { {CommunicationControlPortInfoItem-Reset-ExtIEs} }	OPTIONAL,
	...
}

CommunicationControlPortInfoItem-Reset-ExtIEs NBAP-PROTOCOL-EXTENSION ::= {
	...
}

-- **************************************************************
--
-- RESET RESPONSE
--
-- **************************************************************

ResetResponse ::= SEQUENCE {
	protocolIEs				ProtocolIE-Container	{{ResetResponse-IEs}},
	protocolExtensions		ProtocolExtensionContainer	{{ResetResponse-Extensions}}     		OPTIONAL,
	...
}

ResetResponse-IEs NBAP-PROTOCOL-IES ::= {
	{ID	id-CriticalityDiagnostics		CRITICALITY		ignore		TYPE	CriticalityDiagnostics		PRESENCE	optional},
	...
}

ResetResponse-Extensions NBAP-PROTOCOL-EXTENSION ::= {
	...
}

-- **************************************************************
--
-- INFORMATION EXCHANGE INITIATION REQUEST
--
-- **************************************************************

InformationExchangeInitiationRequest ::= SEQUENCE {
	protocolIEs				ProtocolIE-Container	{{InformationExchangeInitiationRequest-IEs}},
	protocolExtensions		ProtocolExtensionContainer	{{InformationExchangeInitiationRequest-Extensions}}		OPTIONAL,
	...
}

InformationExchangeInitiationRequest-IEs NBAP-PROTOCOL-IES ::= {
	{ ID	id-InformationExchangeID								CRITICALITY	reject			TYPE	InformationExchangeID							PRESENCE	mandatory	}|
	{ ID	id-InformationExchangeObjectType-InfEx-Rqst			CRITICALITY	reject			TYPE 	InformationExchangeObjectType-InfEx-Rqst		PRESENCE 	mandatory	}|
	{ ID	id-InformationType						CRITICALITY	reject			        TYPE	InformationType					PRESENCE	mandatory	}|
	{ ID	id-InformationReportCharacteristics						CRITICALITY	reject			TYPE	InformationReportCharacteristics					PRESENCE	mandatory},
	...
}

InformationExchangeInitiationRequest-Extensions NBAP-PROTOCOL-EXTENSION ::= {
	...
}

InformationExchangeObjectType-InfEx-Rqst ::= CHOICE {
	cell							Cell-InfEx-Rqst,
	...
}

Cell-InfEx-Rqst ::= SEQUENCE {
	c-ID							C-ID,
	iE-Extensions					ProtocolExtensionContainer  { { CellItem-InfEx-Rqst-ExtIEs} }		OPTIONAL,
	...
}

CellItem-InfEx-Rqst-ExtIEs NBAP-PROTOCOL-EXTENSION ::= {
	...
}

-- **************************************************************
--
-- INFORMATION EXCHANGE INITIATION RESPONSE
--
-- **************************************************************

InformationExchangeInitiationResponse ::= SEQUENCE {
	protocolIEs				ProtocolIE-Container	{{InformationExchangeInitiationResponse-IEs}},
	protocolExtensions		ProtocolExtensionContainer	{{InformationExchangeInitiationResponse-Extensions}}		OPTIONAL,
	...
}

InformationExchangeInitiationResponse-IEs NBAP-PROTOCOL-IES ::= {
	{ ID	id-InformationExchangeID							CRITICALITY	ignore			TYPE	InformationExchangeID							PRESENCE	mandatory	}|
	{ ID	id-InformationExchangeObjectType-InfEx-Rsp		CRITICALITY	ignore			TYPE	InformationExchangeObjectType-InfEx-Rsp		PRESENCE	optional	}|
	{ ID	id-CriticalityDiagnostics					CRITICALITY	ignore			TYPE	CriticalityDiagnostics					PRESENCE	optional	},
	...
}

InformationExchangeInitiationResponse-Extensions NBAP-PROTOCOL-EXTENSION ::= {
	...
}

InformationExchangeObjectType-InfEx-Rsp ::= CHOICE {
 	cell						Cell-InfEx-Rsp,
	...
 }

Cell-InfEx-Rsp ::= SEQUENCE {
 	requestedDataValue			    RequestedDataValue,
	iE-Extensions					ProtocolExtensionContainer  { { CellItem-InfEx-Rsp-ExtIEs} }		OPTIONAL,
	...
 }

CellItem-InfEx-Rsp-ExtIEs NBAP-PROTOCOL-EXTENSION ::= {
	...
}

-- **************************************************************
--
-- INFORMATION EXCHANGE INITIATION FAILURE
--
-- **************************************************************

InformationExchangeInitiationFailure ::= SEQUENCE {
	protocolIEs				ProtocolIE-Container	{{InformationExchangeInitiationFailure-IEs}},
	protocolExtensions		ProtocolExtensionContainer	{{InformationExchangeInitiationFailure-Extensions}}		OPTIONAL,
	...
}

InformationExchangeInitiationFailure-IEs NBAP-PROTOCOL-IES ::= {
	{ ID	id-InformationExchangeID				CRITICALITY		ignore			TYPE	InformationExchangeID				PRESENCE	mandatory	}|
	{ ID	id-Cause						CRITICALITY		ignore			TYPE	Cause						PRESENCE	mandatory	}|
	{ ID	id-CriticalityDiagnostics		CRITICALITY		ignore			TYPE	CriticalityDiagnostics		PRESENCE	optional	},
	...
}

InformationExchangeInitiationFailure-Extensions NBAP-PROTOCOL-EXTENSION ::= {
	...
}

-- **************************************************************
--
-- INFORMATION REPORT
--
-- **************************************************************

InformationReport ::= SEQUENCE {
	protocolIEs				ProtocolIE-Container	{{InformationReport-IEs}},
	protocolExtensions		ProtocolExtensionContainer	{{InformationReport-Extensions}}		OPTIONAL,
	...
}

InformationReport-IEs NBAP-PROTOCOL-IES ::= {
	{ ID	id-InformationExchangeID							CRITICALITY	ignore			TYPE	InformationExchangeID							PRESENCE	mandatory	}|
	{ ID	id-InformationExchangeObjectType-InfEx-Rprt		CRITICALITY	ignore			TYPE	InformationExchangeObjectType-InfEx-Rprt		PRESENCE	mandatory	},
	...
}

InformationReport-Extensions NBAP-PROTOCOL-EXTENSION ::= {
	...
}

InformationExchangeObjectType-InfEx-Rprt ::= CHOICE {
	cell							Cell-Inf-Rprt,
	...
 }

Cell-Inf-Rprt ::= SEQUENCE {
	requestedDataValueInformation	RequestedDataValueInformation,
	iE-Extensions					ProtocolExtensionContainer  {{ CellItem-Inf-Rprt-ExtIEs }}		OPTIONAL,
	...

 }

CellItem-Inf-Rprt-ExtIEs NBAP-PROTOCOL-EXTENSION ::= {
	...
}

-- **************************************************************
--
-- INFORMATION EXCHANGE TERMINATION REQUEST
--
-- **************************************************************

InformationExchangeTerminationRequest ::= SEQUENCE {
	protocolIEs				ProtocolIE-Container	{{InformationExchangeTerminationRequest-IEs}},
	protocolExtensions		ProtocolExtensionContainer	{{InformationExchangeTerminationRequest-Extensions}}		OPTIONAL,
	...
}

InformationExchangeTerminationRequest-IEs NBAP-PROTOCOL-IES ::= {
	{ ID	id-InformationExchangeID			CRITICALITY		ignore				TYPE	InformationExchangeID			PRESENCE	mandatory},
	...
}

InformationExchangeTerminationRequest-Extensions NBAP-PROTOCOL-EXTENSION ::= {
	...
}

-- **************************************************************
--
-- INFORMATION EXCHANGE FAILURE INDICATION
--
-- **************************************************************

InformationExchangeFailureIndication ::= SEQUENCE {
	protocolIEs				ProtocolIE-Container	{{InformationExchangeFailureIndication-IEs}},
	protocolExtensions			ProtocolExtensionContainer	{{InformationExchangeFailureIndication-Extensions}}				OPTIONAL,
	...
}

InformationExchangeFailureIndication-IEs NBAP-PROTOCOL-IES ::= {
	{ ID	id-InformationExchangeID			CRITICALITY	ignore			TYPE	InformationExchangeID			PRESENCE	mandatory	}|
	{ ID	id-Cause					CRITICALITY	ignore			TYPE	Cause					PRESENCE	mandatory	},
	...
}

InformationExchangeFailureIndication-Extensions NBAP-PROTOCOL-EXTENSION ::= {
	...
}

-- **************************************************************
--
-- CELL SYNCHRONISATION INITIATION REQUEST TDD
--
-- **************************************************************

CellSynchronisationInitiationRequestTDD ::= SEQUENCE {
	protocolIEs				ProtocolIE-Container	{{CellSynchronisationInitiationRequestTDD-IEs}},
	protocolExtensions		ProtocolExtensionContainer	{{CellSynchronisationInitiationRequestTDD-Extensions}}     OPTIONAL,
	...
}

CellSynchronisationInitiationRequestTDD-Extensions NBAP-PROTOCOL-EXTENSION ::= {
	{ ID	id-SYNCDlCodeId-TransInitLCR-CellSyncInitiationRqstTDD		CRITICALITY 	reject		EXTENSION	SYNCDlCodeId-TransInitLCR-CellSyncInitiationRqstTDD		PRESENCE 	optional	}|	-- 1.28Mcps TDD only
	{ ID	id-SYNCDlCodeId-MeasureInitLCR-CellSyncInitiationRqstTDD		CRITICALITY 	reject		EXTENSION	SYNCDlCodeId-MeasureInitLCR-CellSyncInitiationRqstTDD		PRESENCE 	optional	},	-- 1.28Mcps TDD only
	...
}

CellSynchronisationInitiationRequestTDD-IEs NBAP-PROTOCOL-IES ::= {
	{ ID	id-C-ID							CRITICALITY		reject		TYPE	C-ID							PRESENCE	mandatory	}|
	{ ID	id-cellSyncBurstRepetitionPeriod			CRITICALITY		reject		TYPE	CellSyncBurstRepetitionPeriod		PRESENCE	mandatory	}|
	{ ID	id-timeslotInfo-CellSyncInitiationRqstTDD	CRITICALITY 	reject		TYPE	TimeslotInfo-CellSyncInitiationRqstTDD		PRESENCE 	optional	}|	-- Mandatory for 3.84Mcps TDD only
	{ ID	id-CellSyncBurstTransInit-CellSyncInitiationRqstTDD		CRITICALITY 	reject		TYPE	CellSyncBurstTransInit-CellSyncInitiationRqstTDD		PRESENCE 	optional	}|	-- 3.84Mcps TDD only
	{ ID	id-CellSyncBurstMeasureInit-CellSyncInitiationRqstTDD		CRITICALITY 	reject		TYPE	CellSyncBurstMeasureInit-CellSyncInitiationRqstTDD		PRESENCE 	optional	},	-- 3.84Mcps TDD only
	...
}

CellSyncBurstTransInit-CellSyncInitiationRqstTDD::= SEQUENCE {
	cSBTransmissionID						CSBTransmissionID,
	sfn										SFN,
 	cellSyncBurstCode						CellSyncBurstCode,
	cellSyncBurstCodeShift					CellSyncBurstCodeShift,
	initialDLTransPower						DL-Power,
	iE-Extensions							ProtocolExtensionContainer { { CellSyncBurstTransInit-CellSyncInitiationRqstTDD-ExtIEs} }		OPTIONAL,
	...
 }

CellSyncBurstTransInit-CellSyncInitiationRqstTDD-ExtIEs NBAP-PROTOCOL-EXTENSION ::= {
	...
}

TimeslotInfo-CellSyncInitiationRqstTDD::= SEQUENCE (SIZE (1..15)) OF TimeSlot

CellSyncBurstMeasureInit-CellSyncInitiationRqstTDD::= SEQUENCE {
	cSBMeasurementID						CSBMeasurementID,
	cellSyncBurstCode						CellSyncBurstCode,
	cellSyncBurstCodeShift					CellSyncBurstCodeShift,
	synchronisationReportType				SynchronisationReportType,
	sfn										SFN							OPTIONAL,
	synchronisationReportCharacteristics	SynchronisationReportCharacteristics,
	iE-Extensions							ProtocolExtensionContainer { { CellSyncBurstMeasureInit-CellSyncInitiationRqstTDD-ExtIEs} }		OPTIONAL,
	...
 }

CellSyncBurstMeasureInit-CellSyncInitiationRqstTDD-ExtIEs NBAP-PROTOCOL-EXTENSION ::= {
	...
}

SYNCDlCodeId-TransInitLCR-CellSyncInitiationRqstTDD::= SEQUENCE {
	cSBTransmissionID						CSBTransmissionID,
	sfn										SFN,
	uARFCN									UARFCN,
	sYNCDlCodeId							SYNCDlCodeId,
	dwPCH-Power								DwPCH-Power,
	iE-Extensions							ProtocolExtensionContainer { { SYNCDlCodeId-TransInitLCR-CellSyncInitiationRqstTDD-ExtIEs } }	OPTIONAL,
	...
}

SYNCDlCodeId-TransInitLCR-CellSyncInitiationRqstTDD-ExtIEs NBAP-PROTOCOL-EXTENSION ::= {
	...
}

SYNCDlCodeId-MeasureInitLCR-CellSyncInitiationRqstTDD::= SEQUENCE {
	cSBMeasurementID						CSBMeasurementID,
	sfn										SFN				OPTIONAL,
	uARFCN									UARFCN,
	sYNCDlCodeId							SYNCDlCodeId,
	synchronisationReportType				SynchronisationReportType,
	synchronisationReportCharacteristics	SynchronisationReportCharacteristics,
	iE-Extensions							ProtocolExtensionContainer { { SYNCDlCodeId-MeasureInitLCR-CellSyncInitiationRqstTDD-ExtIEs } }	OPTIONAL,
	...
}

SYNCDlCodeId-MeasureInitLCR-CellSyncInitiationRqstTDD-ExtIEs NBAP-PROTOCOL-EXTENSION ::= {
	...
}

-- **************************************************************
--
-- CELL SYNCHRONISATION INITIATION RESPONSE TDD
--
-- **************************************************************

CellSynchronisationInitiationResponseTDD ::= SEQUENCE {
	protocolIEs				ProtocolIE-Container	{{CellSynchronisationInitiationResponseTDD-IEs}},
	protocolExtensions		ProtocolExtensionContainer	{{CellSynchronisationInitiationResponseTDD-Extensions}}     OPTIONAL,
	...
}

CellSynchronisationInitiationResponseTDD-Extensions NBAP-PROTOCOL-EXTENSION ::= {
	...
}

CellSynchronisationInitiationResponseTDD-IEs NBAP-PROTOCOL-IES ::= {
	{ ID	id-CriticalityDiagnostics					CRITICALITY		ignore		TYPE	CriticalityDiagnostics								PRESENCE	optional	},
	...
}

-- **************************************************************
--
-- CELL SYNCHRONISATION INITIATION FAILURE TDD
--
-- **************************************************************

CellSynchronisationInitiationFailureTDD ::= SEQUENCE {
	protocolIEs				ProtocolIE-Container	{{CellSynchronisationInitiationFailureTDD-IEs}},
	protocolExtensions		ProtocolExtensionContainer	{{CellSynchronisationInitiationFailureTDD-Extensions}}     OPTIONAL,
	...
}

CellSynchronisationInitiationFailureTDD-Extensions NBAP-PROTOCOL-EXTENSION ::= {
	...
}

CellSynchronisationInitiationFailureTDD-IEs NBAP-PROTOCOL-IES ::= {
	{ ID	id-Cause							CRITICALITY		ignore		TYPE	Cause							PRESENCE	mandatory	}|
	{ ID	id-CriticalityDiagnostics			CRITICALITY		ignore		TYPE	CriticalityDiagnostics		PRESENCE	optional	},
	...
}

-- **************************************************************
--
-- CELL SYNCHRONISATION RECONFIGURATION REQUEST TDD
--
-- **************************************************************

CellSynchronisationReconfigurationRequestTDD ::= SEQUENCE {
	protocolIEs				ProtocolIE-Container	{{CellSynchronisationReconfigurationRequestTDD-IEs}},
	protocolExtensions		ProtocolExtensionContainer	{{CellSynchronisationReconfigurationRequestTDD-Extensions}}     OPTIONAL,
	...
}

CellSynchronisationReconfigurationRequestTDD-Extensions NBAP-PROTOCOL-EXTENSION ::= {
	{ ID	id-NSubCyclesPerCyclePeriod-CellSyncReconfRqstTDD		CRITICALITY 	reject		EXTENSION	NSubCyclesPerCyclePeriod		PRESENCE 	optional	}|	-- 1.28Mcps TDD only
	{ ID	id-SYNCDlCodeIdTransReconfInfoLCR-CellSyncReconfRqstTDD		CRITICALITY 	reject		EXTENSION	SYNCDlCodeIdTransReconfInfoLCR-CellSyncReconfRqstTDD		PRESENCE 	optional	}|	-- 1.28Mcps TDD only
	{ ID	id-SYNCDlCodeIdMeasReconfigurationLCR-CellSyncReconfRqstTDD		CRITICALITY 	reject		EXTENSION	SYNCDlCodeIdMeasReconfigurationLCR-CellSyncReconfRqstTDD		PRESENCE 	optional	},	-- 1.28Mcps TDD only
	...
}

CellSynchronisationReconfigurationRequestTDD-IEs NBAP-PROTOCOL-IES ::= {
	{ ID	id-C-ID							CRITICALITY		reject		TYPE	C-ID							PRESENCE		mandatory	}|
	{ ID	id-TimeSlot						CRITICALITY		reject		TYPE	TimeSlot						PRESENCE 	mandatory	}|
	-- 1.28Mcps TDD - There is no Time Slot indication needed, the CRNC should indicate Time Slot 0 and the Node B shall ignore it
	{ ID	id-NCyclesPerSFNperiod			CRITICALITY		reject		TYPE	NCyclesPerSFNperiod			PRESENCE 	mandatory	}|
	{ ID	id-NRepetitionsPerCyclePeriod	CRITICALITY		reject		TYPE	NRepetitionsPerCyclePeriod PRESENCE 	mandatory	}|
	{ ID	id-CellSyncBurstTransReconfInfo-CellSyncReconfRqstTDD		CRITICALITY 	reject		TYPE	CellSyncBurstTransReconfInfo-CellSyncReconfRqstTDD		PRESENCE 	optional	}|	-- 3.84Mcps TDD only
	{ ID	id-CellSyncBurstMeasReconfiguration-CellSyncReconfRqstTDD		CRITICALITY 	reject		TYPE	CellSyncBurstMeasReconfiguration-CellSyncReconfRqstTDD		PRESENCE 	optional	},	-- 3.84Mcps TDD only
	...
}

CellSyncBurstTransReconfInfo-CellSyncReconfRqstTDD ::= SEQUENCE (SIZE (1.. maxNrOfCellSyncBursts)) OF CellSyncBurstTransInfoItem-CellSyncReconfRqstTDD

CellSyncBurstTransInfoItem-CellSyncReconfRqstTDD ::= SEQUENCE {
	cSBTransmissionID							CSBTransmissionID,
	syncFrameNumberToTransmit					SyncFrameNumber,
	cellSyncBurstCode							CellSyncBurstCode			OPTIONAL,
	cellSyncBurstCodeShift						CellSyncBurstCodeShift		OPTIONAL,
	dlTransPower								DL-Power					OPTIONAL,
	iE-Extensions								ProtocolExtensionContainer { { CellSyncBurstTransInfoItem-CellSyncReconfRqstTDD-ExtIEs} }		OPTIONAL,
	...
}

CellSyncBurstTransInfoItem-CellSyncReconfRqstTDD-ExtIEs NBAP-PROTOCOL-EXTENSION ::= {
	...
}

CellSyncBurstMeasReconfiguration-CellSyncReconfRqstTDD ::= ProtocolIE-Single-Container {{ CellSyncBurstMeasInfo-CellSyncReconfRqstTDD }}

CellSyncBurstMeasInfo-CellSyncReconfRqstTDD NBAP-PROTOCOL-IES ::= {
	{ ID id-CellSyncBurstMeasInfoList-CellSyncReconfRqstTDD	CRITICALITY reject	TYPE CellSyncBurstMeasInfoList-CellSyncReconfRqstTDD 	PRESENCE	mandatory }|
	{ ID id-SynchronisationReportType					CRITICALITY reject	TYPE SynchronisationReportType			 				PRESENCE	optional }|
	{ ID id-SynchronisationReportCharacteristics		CRITICALITY reject	TYPE SynchronisationReportCharacteristics		 	PRESENCE	optional },
	...
}

CellSyncBurstMeasInfoList-CellSyncReconfRqstTDD ::= SEQUENCE (SIZE (1.. maxNrOfCellSyncBursts)) OF CellSyncBurstMeasInfoItem-CellSyncReconfRqstTDD

CellSyncBurstMeasInfoItem-CellSyncReconfRqstTDD ::= SEQUENCE {
	syncFrameNrToReceive					SyncFrameNumber,
	syncBurstInfo							CellSyncBurstInfoList-CellSyncReconfRqstTDD,
	...
}

CellSyncBurstInfoList-CellSyncReconfRqstTDD ::= SEQUENCE (SIZE (1..maxNrOfReceptsPerSyncFrame)) OF CellSyncBurstInfoItem-CellSyncReconfRqstTDD

CellSyncBurstInfoItem-CellSyncReconfRqstTDD ::= SEQUENCE {
	cSBMeasurementID							CSBMeasurementID,
	cellSyncBurstCode							CellSyncBurstCode,
	cellSyncBurstCodeShift						CellSyncBurstCodeShift,
	iE-Extensions								ProtocolExtensionContainer { { CellSyncBurstMeasInfo-CellSyncReconfRqstTDD-ExtIEs} }		OPTIONAL,
	...
}

CellSyncBurstMeasInfo-CellSyncReconfRqstTDD-ExtIEs NBAP-PROTOCOL-EXTENSION ::= {
	...
}

SYNCDlCodeIdTransReconfInfoLCR-CellSyncReconfRqstTDD ::= SEQUENCE (SIZE (1..maxNrOfSyncFramesLCR)) OF SYNCDlCodeIdTransReconfItemLCR-CellSyncReconfRqstTDD

SYNCDlCodeIdTransReconfItemLCR-CellSyncReconfRqstTDD ::= SEQUENCE {
	cSBTransmissionID							CSBTransmissionID,
	syncFrameNumberforTransmit					SyncFrameNumber,
	uARFCN										UARFCN,
	sYNCDlCodeId								SYNCDlCodeId	OPTIONAL,
	dwPCH-Power									DwPCH-Power		OPTIONAL,
	iE-Extensions								ProtocolExtensionContainer { { SYNCDlCodeIdTransReconfInfoLCR-CellSyncReconfRqstTDD-ExtIEs} }		OPTIONAL,
	...
}

SYNCDlCodeIdTransReconfInfoLCR-CellSyncReconfRqstTDD-ExtIEs NBAP-PROTOCOL-EXTENSION ::= {
	...
}

SYNCDlCodeIdMeasReconfigurationLCR-CellSyncReconfRqstTDD ::= ProtocolIE-Single-Container {{ SYNCDlCodeIdMeasInfoLCR-CellSyncReconfRqstTDD }}

SYNCDlCodeIdMeasInfoLCR-CellSyncReconfRqstTDD NBAP-PROTOCOL-IES ::= {
	{ ID id-SYNCDlCodeIdMeasInfoList-CellSyncReconfRqstTDD	CRITICALITY reject	TYPE SYNCDlCodeIdMeasInfoList-CellSyncReconfRqstTDD	PRESENCE	mandatory }|
	{ ID id-SynchronisationReportType					CRITICALITY reject	TYPE SynchronisationReportType			 				PRESENCE	optional }|
	{ ID id-SynchronisationReportCharacteristics		CRITICALITY reject	TYPE SynchronisationReportCharacteristics		 	PRESENCE	optional },
	...
}

SYNCDlCodeIdMeasInfoList-CellSyncReconfRqstTDD::= SEQUENCE (SIZE (1.. maxNrOfSyncDLCodesLCR)) OF SYNCDlCodeIdMeasInfoItem-CellSyncReconfRqstTDD

SYNCDlCodeIdMeasInfoItem-CellSyncReconfRqstTDD ::= SEQUENCE {
	syncFrameNrToReceive					SyncFrameNumber,
	sYNCDlCodeIdInfoLCR						SYNCDlCodeIdInfoListLCR-CellSyncReconfRqstTDD,
	iE-Extensions							ProtocolExtensionContainer { { SYNCDlCodeIdMeasInfoItem-CellSyncReconfRqstTDD-ExtIEs} }		OPTIONAL,
	...
}

SYNCDlCodeIdMeasInfoItem-CellSyncReconfRqstTDD-ExtIEs NBAP-PROTOCOL-EXTENSION ::= {
	...
}

SYNCDlCodeIdInfoListLCR-CellSyncReconfRqstTDD ::= SEQUENCE (SIZE (1.. maxNrOfReceptionsperSyncFrameLCR)) OF SYNCDlCodeIdInfoItemLCR-CellSyncReconfRqstTDD

SYNCDlCodeIdInfoItemLCR-CellSyncReconfRqstTDD ::= SEQUENCE {
	cSBMeasurementID							CSBMeasurementID,
	sYNCDlCodeId								SYNCDlCodeId,
	uARFCN										UARFCN,
	propagationDelayCompensation				TimingAdjustmentValue		OPTIONAL,
	iE-Extensions								ProtocolExtensionContainer { { SYNCDlCodeIdInfoLCR-CellSyncReconfRqstTDD-ExtIEs} }		OPTIONAL,
	...
}

SYNCDlCodeIdInfoLCR-CellSyncReconfRqstTDD-ExtIEs NBAP-PROTOCOL-EXTENSION ::= {
	...
}

-- **************************************************************
--
-- CELL SYNCHRONISATION RECONFIGURATION RESPONSE TDD
--
-- **************************************************************

CellSynchronisationReconfigurationResponseTDD ::= SEQUENCE {
	protocolIEs				ProtocolIE-Container	{{CellSynchronisationReconfigurationResponseTDD-IEs}},
	protocolExtensions		ProtocolExtensionContainer	{{CellSynchronisationReconfigurationResponseTDD-Extensions}}     OPTIONAL,
	...
}

CellSynchronisationReconfigurationResponseTDD-Extensions NBAP-PROTOCOL-EXTENSION ::= {
	...
}

CellSynchronisationReconfigurationResponseTDD-IEs NBAP-PROTOCOL-IES ::= {
	{ ID	id-CriticalityDiagnostics					CRITICALITY		ignore		TYPE	CriticalityDiagnostics			PRESENCE	optional	},
	...
}

-- **************************************************************
--
-- CELL SYNCHRONISATION RECONFIGURATION FAILURE TDD
--
-- **************************************************************

CellSynchronisationReconfigurationFailureTDD ::= SEQUENCE {
	protocolIEs				ProtocolIE-Container		{{CellSynchronisationReconfigurationFailureTDD-IEs}},
	protocolExtensions		ProtocolExtensionContainer	{{CellSynchronisationReconfigurationFailureTDD-Extensions}}     OPTIONAL,
	...
}

CellSynchronisationReconfigurationFailureTDD-Extensions NBAP-PROTOCOL-EXTENSION ::= {
	...
}

CellSynchronisationReconfigurationFailureTDD-IEs NBAP-PROTOCOL-IES ::= {
	{ ID	id-Cause							CRITICALITY		ignore		TYPE	Cause							PRESENCE	mandatory	}|
	{ ID	id-CriticalityDiagnostics			CRITICALITY		ignore		TYPE	CriticalityDiagnostics		PRESENCE	optional	},
	...
}

-- **************************************************************
--
-- CELL SYNCHRONISATION ADJUSTMENT REQUEST TDD
--
-- **************************************************************

CellSynchronisationAdjustmentRequestTDD ::= SEQUENCE {
	protocolIEs				ProtocolIE-Container		{{CellSynchronisationAdjustmentRequestTDD-IEs}},
	protocolExtensions		ProtocolExtensionContainer	{{CellSynchronisationAdjustmentRequestTDD-Extensions}}     OPTIONAL,
	...
}

CellSynchronisationAdjustmentRequestTDD-Extensions NBAP-PROTOCOL-EXTENSION ::= {
	...
}

CellSynchronisationAdjustmentRequestTDD-IEs NBAP-PROTOCOL-IES ::= {
	{ ID	id-CellAdjustmentInfo-SyncAdjustmntRqstTDD	CRITICALITY	ignore	TYPE CellAdjustmentInfo-SyncAdjustmentRqstTDD	PRESENCE mandatory	},
	...
}

CellAdjustmentInfo-SyncAdjustmentRqstTDD::= SEQUENCE (SIZE (1..maxCellinNodeB)) OF ProtocolIE-Single-Container {{ CellAdjustmentInfoItemIE-SyncAdjustmntRqstTDD }}

CellAdjustmentInfoItemIE-SyncAdjustmntRqstTDD NBAP-PROTOCOL-IES ::= {
	{ ID id-CellAdjustmentInfoItem-SyncAdjustmentRqstTDD		CRITICALITY		ignore			TYPE		CellAdjustmentInfoItem-SyncAdjustmentRqstTDD		PRESENCE	mandatory }
}

CellAdjustmentInfoItem-SyncAdjustmentRqstTDD ::= SEQUENCE {
	c-ID									C-ID,
	frameAdjustmentValue					FrameAdjustmentValue		OPTIONAL,
	timingAdjustmentValue					TimingAdjustmentValue		OPTIONAL,
	dLTransPower							DL-Power					OPTIONAL, -- 3.84Mcps TDD only
	sfn										SFN							OPTIONAL,
	iE-Extensions							ProtocolExtensionContainer { { CellAdjustmentInfoItem-SyncAdjustmntRqstTDD-ExtIEs} }		OPTIONAL,
	...
 }

CellAdjustmentInfoItem-SyncAdjustmntRqstTDD-ExtIEs NBAP-PROTOCOL-EXTENSION ::= {
	{ ID id-DwPCH-Power		CRITICALITY	ignore EXTENSION	DwPCH-Power		PRESENCE optional }, -- 1.28Mcps TDD only
	...
}

-- **************************************************************
--
-- CELL SYNCHRONISATION ADJUSTMENT RESPONSE TDD
--
-- **************************************************************

CellSynchronisationAdjustmentResponseTDD ::= SEQUENCE {
	protocolIEs				ProtocolIE-Container	{{CellSynchronisationAdjustmentResponseTDD-IEs}},
	protocolExtensions		ProtocolExtensionContainer	{{CellSynchronisationAdjustmentResponseTDD-Extensions}}     OPTIONAL,
	...
}

CellSynchronisationAdjustmentResponseTDD-Extensions NBAP-PROTOCOL-EXTENSION ::= {
	...
}

CellSynchronisationAdjustmentResponseTDD-IEs NBAP-PROTOCOL-IES ::= {
	{ ID	id-CriticalityDiagnostics			CRITICALITY		ignore		TYPE	CriticalityDiagnostics					PRESENCE	optional	},
	...
}

-- **************************************************************
--
-- CELL SYNCHRONISATION ADJUSTMENT FAILURE TDD
--
-- **************************************************************

CellSynchronisationAdjustmentFailureTDD ::= SEQUENCE {
	protocolIEs				ProtocolIE-Container	{{CellSynchronisationAdjustmentFailureTDD-IEs}},
	protocolExtensions		ProtocolExtensionContainer	{{CellSynchronisationAdjustmentFailureTDD-Extensions}}     OPTIONAL,
	...
}

CellSynchronisationAdjustmentFailureTDD-Extensions NBAP-PROTOCOL-EXTENSION ::= {
	...
}

CellSynchronisationAdjustmentFailureTDD-IEs NBAP-PROTOCOL-IES ::= {
	{ ID	id-CauseLevel-SyncAdjustmntFailureTDD	CRITICALITY	ignore		TYPE	CauseLevel-SyncAdjustmntFailureTDD		PRESENCE	mandatory	}|
	{ ID	id-CriticalityDiagnostics				CRITICALITY	ignore		TYPE	CriticalityDiagnostics						PRESENCE	optional	},
	...
}

CauseLevel-SyncAdjustmntFailureTDD ::= CHOICE {
	generalCause			GeneralCauseList-SyncAdjustmntFailureTDD,
	cellSpecificCause		CellSpecificCauseList-SyncAdjustmntFailureTDD,
	...
}

GeneralCauseList-SyncAdjustmntFailureTDD::= SEQUENCE {
	cause										Cause,
	iE-Extensions								ProtocolExtensionContainer { { GeneralCauseList-SyncAdjustmntFailureTDD-ExtIEs} }		OPTIONAL,
	...
}

GeneralCauseList-SyncAdjustmntFailureTDD-ExtIEs NBAP-PROTOCOL-EXTENSION ::= {
	...
}

CellSpecificCauseList-SyncAdjustmntFailureTDD ::= SEQUENCE {
	unsuccessful-cell-InformationRespList-SyncAdjustmntFailureTDD		Unsuccessful-cell-InformationRespList-SyncAdjustmntFailureTDD,
	iE-Extensions								ProtocolExtensionContainer { { CellSpecificCauseList-SyncAdjustmntFailureTDD-ExtIEs} }		OPTIONAL,
	...
}

CellSpecificCauseList-SyncAdjustmntFailureTDD-ExtIEs NBAP-PROTOCOL-EXTENSION ::= {
	...
}

Unsuccessful-cell-InformationRespList-SyncAdjustmntFailureTDD ::= SEQUENCE (SIZE (1..maxNrOfRLs))	OF ProtocolIE-Single-Container {{ Unsuccessful-cell-InformationRespItemIE-SyncAdjustmntFailureTDD }}

Unsuccessful-cell-InformationRespItemIE-SyncAdjustmntFailureTDD NBAP-PROTOCOL-IES ::= {
	{ ID	id-Unsuccessful-cell-InformationRespItem-SyncAdjustmntFailureTDD		CRITICALITY		ignore		TYPE	Unsuccessful-cell-InformationRespItem-SyncAdjustmntFailureTDD		PRESENCE	mandatory},
	...
}

Unsuccessful-cell-InformationRespItem-SyncAdjustmntFailureTDD::= SEQUENCE {
	c-ID										C-ID,
	cause										Cause,
	iE-Extensions								ProtocolExtensionContainer { { Unsuccessful-cell-InformationRespItem-SyncAdjustmntFailureTDD-ExtIEs} }		OPTIONAL,
	...
}

Unsuccessful-cell-InformationRespItem-SyncAdjustmntFailureTDD-ExtIEs NBAP-PROTOCOL-EXTENSION ::= {
	...
}

-- **************************************************************
--
-- CELL SYNCHRONISATION TERMINATION REQUEST TDD
--
-- **************************************************************

CellSynchronisationTerminationRequestTDD ::= SEQUENCE {
	protocolIEs				ProtocolIE-Container	{{CellSynchronisationTerminationRequestTDD-IEs}},
	protocolExtensions		ProtocolExtensionContainer	{{CellSynchronisationTerminationRequestTDD-Extensions}}     OPTIONAL,
	...
}

CellSynchronisationTerminationRequestTDD-Extensions NBAP-PROTOCOL-EXTENSION ::= {
	...
}

CellSynchronisationTerminationRequestTDD-IEs NBAP-PROTOCOL-IES ::= {
	{ ID	id-C-ID							CRITICALITY		ignore		TYPE	C-ID							PRESENCE	mandatory	}|
	{ ID	id-CSBTransmissionID			CRITICALITY		ignore		TYPE	CSBTransmissionID				PRESENCE	optional		}|
	{ ID	id-CSBMeasurementID				CRITICALITY		ignore		TYPE	CSBMeasurementID				PRESENCE	optional		},
	...
}

-- **************************************************************
--
-- CELL SYNCHRONISATION FAILURE INDICATION TDD
--
-- **************************************************************

CellSynchronisationFailureIndicationTDD ::= SEQUENCE {
	protocolIEs				ProtocolIE-Container	{{CellSynchronisationFailureIndicationTDD-IEs}},
	protocolExtensions		ProtocolExtensionContainer	{{CellSynchronisationFailureIndicationTDD-Extensions}}     OPTIONAL,
	...
}

CellSynchronisationFailureIndicationTDD-Extensions NBAP-PROTOCOL-EXTENSION ::= {
	...
}

CellSynchronisationFailureIndicationTDD-IEs NBAP-PROTOCOL-IES ::= {
	{ ID	id-C-ID							CRITICALITY		ignore		TYPE	C-ID							PRESENCE	mandatory	}|
	{ ID	id-CSBTransmissionID			CRITICALITY		ignore		TYPE	CSBTransmissionID				PRESENCE	optional		}|
	{ ID	id-CSBMeasurementID				CRITICALITY		ignore		TYPE	CSBMeasurementID				PRESENCE	optional		}|
	{ ID	id-Cause						CRITICALITY		ignore		TYPE	Cause							PRESENCE	mandatory	},
	...
}

-- **************************************************************
--
-- CELL SYNCHRONISATION REPORT TDD
--
-- **************************************************************

CellSynchronisationReportTDD ::= SEQUENCE {
	protocolIEs				ProtocolIE-Container	{{CellSynchronisationReportTDD-IEs}},
	protocolExtensions		ProtocolExtensionContainer	{{CellSynchronisationReportTDD-Extensions}}     OPTIONAL,
	...
}

CellSynchronisationReportTDD-Extensions NBAP-PROTOCOL-EXTENSION ::= {
	...
}

CellSynchronisationReportTDD-IEs NBAP-PROTOCOL-IES ::= {
	{ ID	id-CellSyncInfo-CellSyncReprtTDD		CRITICALITY	ignore		TYPE	CellSyncInfo-CellSyncReprtTDD			PRESENCE	mandatory	},
	...
}


CellSyncInfo-CellSyncReprtTDD ::= SEQUENCE (SIZE (1..maxCellinNodeB))	OF ProtocolIE-Single-Container {{ CellSyncInfoItemIE-CellSyncReprtTDD }}

CellSyncInfoItemIE-CellSyncReprtTDD NBAP-PROTOCOL-IES ::= {
	{ ID	id-C-ID											CRITICALITY	ignore	TYPE C-ID													PRESENCE	mandatory}|
	{ ID	id-SyncReportType-CellSyncReprtTDD		CRITICALITY	ignore		TYPE SyncReportType-CellSyncReprtTDD		PRESENCE	optional},
	...
}

SyncReportType-CellSyncReprtTDD ::= CHOICE {
	intStdPhSyncInfo-CellSyncReprtTDD		IntStdPhCellSyncInfo-CellSyncReprtTDD,
	lateEntrantCell				NULL,
	frequencyAcquisition		NULL,
	...
}

IntStdPhCellSyncInfo-CellSyncReprtTDD ::= SEQUENCE {
	cellSyncBurstMeasuredInfo					CellSyncBurstMeasInfoList-CellSyncReprtTDD,
	iE-Extensions								ProtocolExtensionContainer { { IntStdPhCellSyncInfoList-CellSyncReprtTDD-ExtIEs} }		OPTIONAL,
	...
}

IntStdPhCellSyncInfoList-CellSyncReprtTDD-ExtIEs NBAP-PROTOCOL-EXTENSION ::= {
	{ ID id-AccumulatedClockupdate-CellSyncReprtTDD		CRITICALITY	ignore EXTENSION TimingAdjustmentValue PRESENCE optional } |
	{ ID id-SyncDLCodeIdsMeasInfoList-CellSyncReprtTDD  CRITICALITY ignore EXTENSION SyncDLCodeIdsMeasInfoList-CellSyncReprtTDD PRESENCE optional }, -- Mandatory for 1.28 Mcps TDD only
	...
}

CellSyncBurstMeasInfoList-CellSyncReprtTDD ::= SEQUENCE (SIZE (0.. maxNrOfCellSyncBursts)) OF CellSyncBurstMeasInfoItem-CellSyncReprtTDD -- Mandatory for 3.84Mcps TDD only

CellSyncBurstMeasInfoItem-CellSyncReprtTDD ::= SEQUENCE {
	sFN										SFN,
	cellSyncBurstInfo-CellSyncReprtTDD		SEQUENCE (SIZE (1..maxNrOfReceptsPerSyncFrame)) OF CellSyncBurstInfo-CellSyncReprtTDD,
	...
}

CellSyncBurstInfo-CellSyncReprtTDD ::= CHOICE {
	cellSyncBurstAvailable		CellSyncBurstAvailable-CellSyncReprtTDD,
	cellSyncBurstNotAvailable	NULL,
	...
}

CellSyncBurstAvailable-CellSyncReprtTDD ::= SEQUENCE {
	cellSyncBurstTiming			CellSyncBurstTiming,
	cellSyncBurstSIR			CellSyncBurstSIR,
	...
}

SyncDLCodeIdsMeasInfoList-CellSyncReprtTDD ::= SEQUENCE (SIZE (0..maxNrOfSyncFramesLCR)) OF SyncDLCodeIdsMeasInfoItem-CellSyncReprtTDD
-- Mandatory for 1.28Mcps TDD only

SyncDLCodeIdsMeasInfoItem-CellSyncReprtTDD ::= SEQUENCE {
	sFN										SFN,
	syncDLCodeIdInfo-CellSyncReprtTDD		SyncDLCodeIdInfo-CellSyncReprtTDD,
	iE-Extensions							ProtocolExtensionContainer { { SyncDLCodeIdsMeasInfoItem-CellSyncReprtTDD-ExtIEs } }		OPTIONAL,
	...
}

SyncDLCodeIdsMeasInfoItem-CellSyncReprtTDD-ExtIEs NBAP-PROTOCOL-EXTENSION ::= {
	...
}

SyncDLCodeIdInfo-CellSyncReprtTDD ::= SEQUENCE (SIZE (1..maxNrOfReceptionsperSyncFrameLCR)) OF SyncDLCodeIdItem-CellSyncReprtTDD

SyncDLCodeIdItem-CellSyncReprtTDD ::= CHOICE {
	syncDLCodeIdAvailable				SyncDLCodeIdAvailable-CellSyncReprtTDD,
	syncDLCodeIDNotAvailable			NULL,
	...
}

SyncDLCodeIdAvailable-CellSyncReprtTDD ::= SEQUENCE {
	syncDLCodeIdTiming			CellSyncBurstTiming,
	syncDLCodeIdSIR				CellSyncBurstSIR,
	iE-Extensions				ProtocolExtensionContainer { { SyncDLCodeIdAvailable-CellSyncReprtTDD-ExtIEs } }		OPTIONAL,
	...
}

SyncDLCodeIdAvailable-CellSyncReprtTDD-ExtIEs NBAP-PROTOCOL-EXTENSION ::= {
	...
}

-- **************************************************************
--
-- BEARER REARRANGEMENT INDICATION
--
-- **************************************************************

BearerRearrangementIndication ::= SEQUENCE {
	protocolIEs                     ProtocolIE-Container       {{BearerRearrangementIndication-IEs}},
	protocolExtensions              ProtocolExtensionContainer {{BearerRearrangementIndication-Extensions}}                   OPTIONAL,
	...
}

BearerRearrangementIndication-IEs NBAP-PROTOCOL-IES ::= {
	{ ID	id-CRNC-CommunicationContextID					CRITICALITY		ignore			TYPE	CRNC-CommunicationContextID				PRESENCE	mandatory		} |
	{ ID	id-SignallingBearerRequestIndicator					CRITICALITY		ignore			TYPE	SignallingBearerRequestIndicator		PRESENCE	optional		} |
	{ ID	id-DCH-RearrangeList-Bearer-RearrangeInd				CRITICALITY		ignore		TYPE	DCH-RearrangeList-Bearer-RearrangeInd				PRESENCE	optional	} |
	{ ID	id-DSCH-RearrangeList-Bearer-RearrangeInd				CRITICALITY		ignore		TYPE	DSCH-RearrangeList-Bearer-RearrangeInd				PRESENCE	optional	} |
	{ ID	id-USCH-RearrangeList-Bearer-RearrangeInd				CRITICALITY		ignore		TYPE	USCH-RearrangeList-Bearer-RearrangeInd				PRESENCE	optional	} |
	{ ID	id-TFCI2BearerRequestIndicator					CRITICALITY		ignore			TYPE	TFCI2BearerRequestIndicator		PRESENCE	optional		}|
	{ ID	id-HSDSCH-RearrangeList-Bearer-RearrangeInd				CRITICALITY		ignore		TYPE	HSDSCH-RearrangeList-Bearer-RearrangeInd				PRESENCE	optional	},
	...
}

BearerRearrangementIndication-Extensions NBAP-PROTOCOL-EXTENSION ::= {
	...
}

DCH-RearrangeList-Bearer-RearrangeInd ::= SEQUENCE (SIZE (1..maxNrOfDCHs)) OF DCH-RearrangeItem-Bearer-RearrangeInd

DCH-RearrangeItem-Bearer-RearrangeInd ::= SEQUENCE {
	dCH-ID											DCH-ID,
	iE-Extensions									ProtocolExtensionContainer { { DCH-RearrangeItem-Bearer-RearrangeInd-ExtIEs} }		OPTIONAL,
	...
}

DCH-RearrangeItem-Bearer-RearrangeInd-ExtIEs  NBAP-PROTOCOL-EXTENSION ::= {
	...
}

DSCH-RearrangeList-Bearer-RearrangeInd ::= SEQUENCE (SIZE (1..maxNrOfDSCHs)) OF DSCH-RearrangeItem-Bearer-RearrangeInd

DSCH-RearrangeItem-Bearer-RearrangeInd ::= SEQUENCE {
	dSCH-ID											DSCH-ID,
	iE-Extensions									ProtocolExtensionContainer { { DSCH-RearrangeItem-Bearer-RearrangeInd-ExtIEs} }		OPTIONAL,
	...
}

DSCH-RearrangeItem-Bearer-RearrangeInd-ExtIEs  NBAP-PROTOCOL-EXTENSION ::= {
	...
}

USCH-RearrangeList-Bearer-RearrangeInd ::= SEQUENCE (SIZE (1..maxNrOfUSCHs)) OF USCH-RearrangeItem-Bearer-RearrangeInd

USCH-RearrangeItem-Bearer-RearrangeInd ::= SEQUENCE {
	uSCH-ID											USCH-ID,
	iE-Extensions									ProtocolExtensionContainer { { USCH-RearrangeItem-Bearer-RearrangeInd-ExtIEs} }		OPTIONAL,
	...
}

USCH-RearrangeItem-Bearer-RearrangeInd-ExtIEs  NBAP-PROTOCOL-EXTENSION ::= {
	...
}

HSDSCH-RearrangeList-Bearer-RearrangeInd ::= SEQUENCE (SIZE (1..maxNrOfMACdFlows)) OF HSDSCH-RearrangeItem-Bearer-RearrangeInd

HSDSCH-RearrangeItem-Bearer-RearrangeInd ::= SEQUENCE {
	hsDSCH-MACdFlow-ID								HSDSCH-MACdFlow-ID,
	iE-Extensions									ProtocolExtensionContainer { { HSDSCH-RearrangeItem-Bearer-RearrangeInd-ExtIEs} }		OPTIONAL,
	...
}

HSDSCH-RearrangeItem-Bearer-RearrangeInd-ExtIEs  NBAP-PROTOCOL-EXTENSION ::= {
	...
}

-- **************************************************************
--
-- RADIO LINK ACTIVATION COMMAND FDD
--
-- **************************************************************

RadioLinkActivationCommandFDD ::= SEQUENCE {
	protocolIEs				ProtocolIE-Container	{{RadioLinkActivationCommandFDD-IEs}},
	protocolExtensions		ProtocolExtensionContainer	{{RadioLinkActivationCommandFDD-Extensions}}			OPTIONAL,
	...
}

RadioLinkActivationCommandFDD-IEs NBAP-PROTOCOL-IES ::= {
	{ ID	id-NodeB-CommunicationContextID						CRITICALITY	reject	TYPE	NodeB-CommunicationContextID								PRESENCE	mandatory	}|
	{ ID	id-DelayedActivationList-RL-ActivationCmdFDD		CRITICALITY	reject	TYPE	DelayedActivationInformationList-RL-ActivationCmdFDD			PRESENCE	mandatory	},
	...
}

RadioLinkActivationCommandFDD-Extensions NBAP-PROTOCOL-EXTENSION ::= {
	...
}

DelayedActivationInformationList-RL-ActivationCmdFDD ::= SEQUENCE (SIZE (1..maxNrOfRLs)) OF ProtocolIE-Single-Container { 
	{ DelayedActivationInformation-RL-ActivationCmdFDD-IEs} }

DelayedActivationInformation-RL-ActivationCmdFDD-IEs NBAP-PROTOCOL-IES ::= {
	{ ID id-DelayedActivationInformation-RL-ActivationCmdFDD	CRITICALITY reject	TYPE DelayedActivationInformation-RL-ActivationCmdFDD	PRESENCE optional	}
}

DelayedActivationInformation-RL-ActivationCmdFDD ::= SEQUENCE {
	rL-ID						RL-ID,
	delayed-activation-update	DelayedActivationUpdate,
	iE-Extensions				ProtocolExtensionContainer { { DelayedActivationInformation-RL-ActivationCmdFDD-ExtIEs} } OPTIONAL,
	...
}

DelayedActivationInformation-RL-ActivationCmdFDD-ExtIEs NBAP-PROTOCOL-EXTENSION ::= {
	...
}

-- **************************************************************
--
-- RADIO LINK ACTIVATION COMMAND TDD
--
-- **************************************************************

RadioLinkActivationCommandTDD ::= SEQUENCE {
	protocolIEs				ProtocolIE-Container	{{RadioLinkActivationCommandTDD-IEs}},
	protocolExtensions		ProtocolExtensionContainer	{{RadioLinkActivationCommandTDD-Extensions}}			OPTIONAL,
	...
}

RadioLinkActivationCommandTDD-IEs NBAP-PROTOCOL-IES ::= {
	{ ID	id-NodeB-CommunicationContextID						CRITICALITY	reject	TYPE	NodeB-CommunicationContextID								PRESENCE	mandatory	}|
	{ ID	id-DelayedActivationList-RL-ActivationCmdTDD		CRITICALITY	reject	TYPE	DelayedActivationInformationList-RL-ActivationCmdTDD			PRESENCE	mandatory	},
	...
}

RadioLinkActivationCommandTDD-Extensions NBAP-PROTOCOL-EXTENSION ::= {
	...
}

DelayedActivationInformationList-RL-ActivationCmdTDD ::= SEQUENCE (SIZE (1..maxNrOfRLs)) OF ProtocolIE-Single-Container { 
	{ DelayedActivationInformation-RL-ActivationCmdTDD-IEs} }

DelayedActivationInformation-RL-ActivationCmdTDD-IEs NBAP-PROTOCOL-IES ::= {
	{ ID id-DelayedActivationInformation-RL-ActivationCmdTDD	CRITICALITY reject	TYPE DelayedActivationInformation-RL-ActivationCmdTDD	PRESENCE optional	}
}

DelayedActivationInformation-RL-ActivationCmdTDD ::= SEQUENCE {
	rL-ID						RL-ID,
	delayed-activation-update	DelayedActivationUpdate,
	iE-Extensions				ProtocolExtensionContainer { { DelayedActivationInformation-RL-ActivationCmdTDD-ExtIEs} } OPTIONAL,
	...
}

DelayedActivationInformation-RL-ActivationCmdTDD-ExtIEs NBAP-PROTOCOL-EXTENSION ::= {
	...
}

-- **************************************************************
--
-- RADIO LINK PARAMETER UPDATE INDICATION FDD
--
-- **************************************************************

RadioLinkParameterUpdateIndicationFDD ::= SEQUENCE {
	protocolIEs				ProtocolIE-Container	{{RadioLinkParameterUpdateIndicationFDD-IEs}},
	protocolExtensions		ProtocolExtensionContainer	{{RadioLinkParameterUpdateIndicationFDD-Extensions}}		OPTIONAL,
	...
}

RadioLinkParameterUpdateIndicationFDD-IEs NBAP-PROTOCOL-IES ::= {
	{ ID id-CRNC-CommunicationContextID			CRITICALITY		reject		TYPE	NodeB-CommunicationContextID			PRESENCE	mandatory	} |
	{ ID id-HSDSCH-FDD-Update-Information		CRITICALITY		reject		TYPE	HSDSCH-FDD-Update-Information			PRESENCE	optional	},
	...
}

RadioLinkParameterUpdateIndicationFDD-Extensions NBAP-PROTOCOL-EXTENSION ::= {
	...
}

-- **************************************************************
--
-- RADIO LINK PARAMETER UPDATE INDICATION TDD
--
-- **************************************************************

RadioLinkParameterUpdateIndicationTDD ::= SEQUENCE {
	protocolIEs				ProtocolIE-Container	{{RadioLinkParameterUpdateIndicationTDD-IEs}},
	protocolExtensions		ProtocolExtensionContainer	{{RadioLinkParameterUpdateIndicationTDD-Extensions}}		OPTIONAL,
	...
}

RadioLinkParameterUpdateIndicationTDD-IEs NBAP-PROTOCOL-IES ::= {
	{ ID id-CRNC-CommunicationContextID			CRITICALITY		reject		TYPE	NodeB-CommunicationContextID			PRESENCE	mandatory	} |
	{ ID id-HSDSCH-TDD-Update-Information		CRITICALITY		reject		TYPE	HSDSCH-TDD-Update-Information			PRESENCE	optional	},
	...
}

RadioLinkParameterUpdateIndicationTDD-Extensions NBAP-PROTOCOL-EXTENSION ::= {
	...
}

END

--******************************************************************************
--
-- Information Element Definitions
--
--******************************************************************************

NBAP-IEs {
itu-t (0) identified-organization (4) etsi (0) mobileDomain (0) 
umts-Access (20) modules (3) nbap (2) version1 (1) nbap-IEs (2) }

DEFINITIONS AUTOMATIC TAGS ::=
BEGIN

IMPORTS
	maxNrOfRLs,
	maxNrOfTFCs,
	maxNrOfErrors,
	maxCTFC,
	maxNrOfTFs,
	maxTTI-count,
	maxRateMatching,
	maxCodeNrComp-1,
	maxNrOfCellSyncBursts,
	maxNrOfCodeGroups,
	maxNrOfMeasNCell,
	maxNrOfMeasNCell-1,
	maxNrOfReceptsPerSyncFrame,
	maxNrOfTFCIGroups,
	maxNrOfTFCI1Combs,
	maxNrOfTFCI2Combs,
	maxNrOfTFCI2Combs-1,
	maxNrOfSF,
	maxTGPS,
	maxNrOfUSCHs,
	maxNrOfULTSs,
	maxNrOfULTSLCRs,
	maxNrOfDPCHs,
	maxNrOfDPCHLCRs,
	maxNrOfCodes,
	maxNrOfDSCHs,
	maxNrOfDLTSs,
	maxNrOfDLTSLCRs,
	maxNrOfDCHs,
	maxNrOfLevels,
    maxNoGPSItems,
    maxNoSat,
	maxNrOfHSSCCHs,
	maxNrOfHSSCCHCodes,
	maxNrOfMACdFlows,
	maxNrOfMACdFlows-1,
	maxNrOfMACdPDUIndexes,
	maxNrOfMACdPDUIndexes-1,
	maxNrOfPriorityQueues,
	maxNrOfPriorityQueues-1,
	maxNrOfHARQProcesses,
	maxNrOfSyncDLCodesLCR,
	maxNrOfSyncFramesLCR,

	id-MessageStructure,
	id-ReportCharacteristicsType-OnModification,
	id-Rx-Timing-Deviation-Value-LCR,
	id-SFNSFNMeasurementValueInformation,
	id-SFNSFNMeasurementThresholdInformation,
	id-TUTRANGPSMeasurementValueInformation,
	id-TUTRANGPSMeasurementThresholdInformation,
	id-TypeOfError,
	id-transportlayeraddress,
	id-bindingID,
	id-Angle-Of-Arrival-Value-LCR,
	id-SyncDLCodeIdThreInfoLCR,
	id-neighbouringTDDCellMeasurementInformationLCR
FROM NBAP-Constants

	Criticality,
	ProcedureID,
	ProtocolIE-ID,
	TransactionID,
	TriggeringMessage
FROM NBAP-CommonDataTypes

	NBAP-PROTOCOL-IES,
	ProtocolExtensionContainer{},
	ProtocolIE-Single-Container{},
	NBAP-PROTOCOL-EXTENSION		
FROM NBAP-Containers;

-- ==========================================
--	A
-- ==========================================

AckNack-RepetitionFactor ::= INTEGER (1..4,...)
-- Step: 1

Ack-Power-Offset ::= INTEGER (0..8,...)
-- According to mapping in ref. [9] subclause 4.2.1

Acknowledged-PCPCH-access-preambles ::= INTEGER (0..15,...)
-- According to mapping in [22].

Acknowledged-PRACH-preambles-Value ::= INTEGER(0..240,...)
-- According to mapping in [22].

AddorDeleteIndicator ::= ENUMERATED {
	add,
	delete
}

Active-Pattern-Sequence-Information ::= SEQUENCE {
	cMConfigurationChangeCFN								CFN,
	transmission-Gap-Pattern-Sequence-Status	Transmission-Gap-Pattern-Sequence-Status-List	OPTIONAL,
	iE-Extensions								ProtocolExtensionContainer { {Active-Pattern-Sequence-Information-ExtIEs} } OPTIONAL,
	...
}

Active-Pattern-Sequence-Information-ExtIEs NBAP-PROTOCOL-EXTENSION ::= {
	...
}

Transmission-Gap-Pattern-Sequence-Status-List ::= SEQUENCE (SIZE (0..maxTGPS)) OF
	SEQUENCE {
		tGPSID			TGPSID,
		tGPRC			TGPRC,
		tGCFN			CFN,
		iE-Extensions		ProtocolExtensionContainer { { Transmission-Gap-Pattern-Sequence-Status-List-ExtIEs } } OPTIONAL,
		...
}

Transmission-Gap-Pattern-Sequence-Status-List-ExtIEs NBAP-PROTOCOL-EXTENSION ::= {
	...
}

AICH-Power ::= INTEGER (-22..5)
-- Offset in dB.

AICH-TransmissionTiming ::= ENUMERATED {
	v0,
	v1
}

AllocationRetentionPriority ::= SEQUENCE {
	priorityLevel				PriorityLevel,
	pre-emptionCapability		Pre-emptionCapability,
	pre-emptionVulnerability	Pre-emptionVulnerability,
	iE-Extensions				ProtocolExtensionContainer { {AllocationRetentionPriority-ExtIEs} } OPTIONAL,
	...
}

AllocationRetentionPriority-ExtIEs NBAP-PROTOCOL-EXTENSION ::= {
	...
}

Angle-Of-Arrival-Value-LCR ::= SEQUENCE {
	aOA-LCR						AOA-LCR,
	aOA-LCR-Accuracy-Class		AOA-LCR-Accuracy-Class,
	iE-Extensions				ProtocolExtensionContainer { {Angle-Of-Arrival-Value-LCR-ExtIEs} } OPTIONAL,
...
}

Angle-Of-Arrival-Value-LCR-ExtIEs NBAP-PROTOCOL-EXTENSION ::= {
	...
}

AOA-LCR ::= INTEGER (0..719)
-- Angle Of Arrival for 1.28Mcps TDD

AOA-LCR-Accuracy-Class	::= ENUMERATED {a,b,c,d,e,f,g,h,...}

APPreambleSignature ::= INTEGER (0..15)

APSubChannelNumber ::= INTEGER (0..11)

AvailabilityStatus ::= ENUMERATED {
	empty,
	in-test,
	failed,
	power-off,
	off-line,
	off-duty,
	dependency,
	degraded,
	not-installed,
	log-full,
	...
}

-- ==========================================
--	B
-- ==========================================

BCCH-ModificationTime ::= INTEGER  (0..511)
-- Time = BCCH-ModificationTime * 8
-- Range 0 to 4088, step 8
-- All SFN values in which MIB may be mapped are allowed

BindingID ::= OCTET STRING (SIZE (1..4, ...))
-- If the Binding ID includes a UDP port, the UDP port is included in octet 1 and 2.The first octet of
-- the UDP port field is included in the first octet of the Binding ID.

BetaCD ::= INTEGER (0..15)

BlockingPriorityIndicator ::= ENUMERATED {
	high,
	normal,
	low,
	...
}
-- High priority: Block resource immediately.
-- Normal priority: Block resource when idle or upon timer expiry.
-- Low priority: Block resource when idle.

SCTD-Indicator ::= ENUMERATED {
	active,
	inactive
}

-- ==========================================
--	C
-- ==========================================

Cause ::= CHOICE {
	radioNetwork			CauseRadioNetwork,
	transport			CauseTransport,
	protocol				CauseProtocol,
	misc					CauseMisc,
	...
}

CauseMisc ::= ENUMERATED {
	control-processing-overload,
	hardware-failure,
	oam-intervention,
	not-enough-user-plane-processing-resources,
	unspecified,
	...
}

CauseProtocol ::= ENUMERATED {
	transfer-syntax-error,
	abstract-syntax-error-reject,
	abstract-syntax-error-ignore-and-notify,
	message-not-compatible-with-receiver-state,
	semantic-error,
	unspecified,
	abstract-syntax-error-falsely-constructed-message,
	...
}

CauseRadioNetwork ::= ENUMERATED {
	unknown-C-ID,
	cell-not-available,
	power-level-not-supported, 
	dl-radio-resources-not-available,
	ul-radio-resources-not-available,
	rl-already-ActivatedOrAllocated,
	nodeB-Resources-unavailable,
	measurement-not-supported-for-the-object,
	combining-resources-not-available,
	requested-configuration-not-supported,
	synchronisation-failure,
	priority-transport-channel-established,
	sIB-Origination-in-Node-B-not-Supported,
	requested-tx-diversity-mode-not-supported,
	unspecified,
	bCCH-scheduling-error,
	measurement-temporarily-not-available,
	invalid-CM-settings,
	reconfiguration-CFN-not-elapsed,
	number-of-DL-codes-not-supported,
	s-cipch-not-supported,
	combining-not-supported,
	ul-sf-not-supported,
	dl-SF-not-supported, 
	common-transport-channel-type-not-supported,
	dedicated-transport-channel-type-not-supported,
	downlink-shared-channel-type-not-supported,
	uplink-shared-channel-type-not-supported,
	cm-not-supported,
	tx-diversity-no-longer-supported,
	unknown-Local-Cell-ID,
	...,
    number-of-UL-codes-not-supported,
    information-temporarily-not-available,
    information-provision-not-supported-for-the-object,
	cell-synchronisation-not-supported,
	cell-synchronisation-adjustment-not-supported,
	dpc-mode-change-not-supported,
	iPDL-already-activated,
	iPDL-not-supported,
	iPDL-parameters-not-available,
	frequency-acquisition-not-supported,
	power-balancing-status-not-compatible,
	requested-typeofbearer-re-arrangement-not-supported,
	signalling-Bearer-Re-arrangement-not-supported,
	bearer-Re-arrangement-needed,
	delayed-activation-not-supported,
	rl-timing-adjustment-not-supported
}

CauseTransport ::= ENUMERATED {
	transport-resource-unavailable,
	unspecified,
	...
}

CCTrCH-ID ::= INTEGER (0..15)

CDSubChannelNumbers ::= BIT STRING {
										subCh11(0),
										subCh10(1),
									 	subCh9(2),
									 	subCh8(3),
									 	subCh7(4),
									 	subCh6(5),
									 	subCh5(6),
									 	subCh4(7),
									 	subCh3(8),
									 	subCh2(9),
									 	subCh1(10),
									 	subCh0(11)
										} (SIZE (12))

CellParameterID ::= INTEGER (0..127,...)

CellSyncBurstCode ::= INTEGER(0..7, ...)

CellSyncBurstCodeShift ::= INTEGER(0..7)

CellSyncBurstRepetitionPeriod ::= INTEGER (0..4095)

CellSyncBurstSIR ::= INTEGER (0..31)

CellSyncBurstTiming ::= CHOICE {
	initialPhase		INTEGER (0..1048575),
	steadyStatePhase		INTEGER (0..255)
}

CellSyncBurstTimingThreshold ::= INTEGER(0..254)

CFN ::= INTEGER (0..255)

Channel-Assignment-Indication ::= ENUMERATED {
	cA-Active,
	cA-Inactive
}

ChipOffset ::= INTEGER (0..38399)
-- Unit Chip

C-ID ::= INTEGER (0..65535)

Closedlooptimingadjustmentmode	::= ENUMERATED {
	adj-1-slot,
	adj-2-slot,
	...
}

CommonChannelsCapacityConsumptionLaw ::= SEQUENCE (SIZE(1..maxNrOfSF)) OF
	SEQUENCE {
		dl-Cost		INTEGER (0..65535),
		ul-Cost		INTEGER (0..65535),
		iE-Extensions		ProtocolExtensionContainer { { CommonChannelsCapacityConsumptionLaw-ExtIEs } }		OPTIONAL,
		...
}

CommonChannelsCapacityConsumptionLaw-ExtIEs NBAP-PROTOCOL-EXTENSION ::= {
	...
}

CommonMeasurementAccuracy ::= CHOICE {
	tUTRANGPSMeasurementAccuracyClass		TUTRANGPSAccuracyClass,
	...
}

CommonMeasurementType ::= ENUMERATED  {
	received-total-wide-band-power,
	transmitted-carrier-power,
	acknowledged-prach-preambles,
	ul-timeslot-iscp,
	acknowledged-PCPCH-access-preambles,
	detected-PCPCH-access-preambles,
	...,
	uTRAN-GPS-Timing-of-Cell-Frames-for-UE-Positioning, 
	sFN-SFN-Observed-Time-Difference
}

CommonMeasurementValue ::= CHOICE {
	transmitted-carrier-power				Transmitted-Carrier-Power-Value,
	received-total-wide-band-power			Received-total-wide-band-power-Value,
	acknowledged-prach-preambles			Acknowledged-PRACH-preambles-Value,
	uL-TimeslotISCP							UL-TimeslotISCP-Value,
	acknowledged-PCPCH-access-preambles		Acknowledged-PCPCH-access-preambles,
	detected-PCPCH-access-preambles			Detected-PCPCH-access-preambles,
	...,
	extension-CommonMeasurementValue		Extension-CommonMeasurementValue
}

Extension-CommonMeasurementValue	::= ProtocolIE-Single-Container {{ Extension-CommonMeasurementValueIE }}

Extension-CommonMeasurementValueIE NBAP-PROTOCOL-IES ::= {
	{ ID id-TUTRANGPSMeasurementValueInformation	CRITICALITY ignore	TYPE TUTRANGPSMeasurementValueInformation	PRESENCE mandatory }|
	{ ID id-SFNSFNMeasurementValueInformation	CRITICALITY ignore	TYPE SFNSFNMeasurementValueInformation		PRESENCE mandatory }
}

CommonMeasurementValueInformation ::= CHOICE {
	measurementAvailable		CommonMeasurementAvailable,
	measurementnotAvailable		CommonMeasurementnotAvailable
}

CommonMeasurementAvailable::= SEQUENCE {
	commonmeasurementValue		CommonMeasurementValue,
	ie-Extensions					ProtocolExtensionContainer { { CommonMeasurementAvailableItem-ExtIEs} }		OPTIONAL,
	...
}

CommonMeasurementAvailableItem-ExtIEs NBAP-PROTOCOL-EXTENSION ::= {
	...
}
CommonMeasurementnotAvailable ::= NULL

CommonPhysicalChannelID ::= INTEGER (0..255)

Common-PhysicalChannel-Status-Information ::= SEQUENCE {
	commonPhysicalChannelID			CommonPhysicalChannelID,
	resourceOperationalState			ResourceOperationalState,
	availabilityStatus					AvailabilityStatus,
	iE-Extensions						ProtocolExtensionContainer  { { Common-PhysicalChannel-Status-Information-ExtIEs} }		OPTIONAL,
	...
}

Common-PhysicalChannel-Status-Information-ExtIEs NBAP-PROTOCOL-EXTENSION ::= {
	...
}

CommonTransportChannelID ::= INTEGER (0..255)

CommonTransportChannel-InformationResponse ::= SEQUENCE {
	commonTransportChannelID			CommonTransportChannelID,
	bindingID							BindingID				OPTIONAL,
	transportLayerAddress				TransportLayerAddress	OPTIONAL,
	iE-Extensions						ProtocolExtensionContainer  { { CommonTransportChannel-InformationResponse-ExtIEs} }		OPTIONAL,
	...
}

CommonTransportChannel-InformationResponse-ExtIEs NBAP-PROTOCOL-EXTENSION ::= {
	...
}

Common-TransportChannel-Status-Information ::= SEQUENCE {
	commonTransportChannelID			CommonTransportChannelID,
	resourceOperationalState			ResourceOperationalState,
	availabilityStatus					AvailabilityStatus,
	iE-Extensions						ProtocolExtensionContainer  { { Common-TransportChannel-Status-Information-ExtIEs} }		OPTIONAL,
	...
}

Common-TransportChannel-Status-Information-ExtIEs NBAP-PROTOCOL-EXTENSION ::= {
	...
}

CommunicationControlPortID ::= INTEGER (0..65535)

Compressed-Mode-Deactivation-Flag::= ENUMERATED {
	deactivate,
	maintain-Active
}

ConfigurationGenerationID ::= INTEGER (0..255)
-- Value '0' means "No configuration" 

ConstantValue ::= INTEGER (-10..10,...)
-- -10 dB - +10 dB
-- unit dB
-- step 1 dB

CPCH-Allowed-Total-Rate ::= ENUMERATED {
	v15,
	v30, 
	v60,
	v120,
	v240,
	v480,
	v960,
	v1920,
	v2880,
	v3840,
	v4800,
	v5760,
	...
}

CPCHScramblingCodeNumber ::= INTEGER (0..79)

CPCH-UL-DPCCH-SlotFormat ::= INTEGER (0..2,...)

CQI-Feedback-Cycle ::= ENUMERATED {v0, v1, v5, v10, v20, v40, v80,...}

CQI-Power-Offset ::= INTEGER (0..8,...)
-- According to mapping in ref. [9] subclause 4.2.1

CQI-RepetitionFactor ::= INTEGER (1..4,...)
-- Step: 1

CriticalityDiagnostics ::= SEQUENCE {
	procedureID					ProcedureID				OPTIONAL,
	triggeringMessage			TriggeringMessage			OPTIONAL,
	procedureCriticality		Criticality				OPTIONAL,
	transactionID				TransactionID				OPTIONAL,
	iEsCriticalityDiagnostics	CriticalityDiagnostics-IE-List	OPTIONAL,
	iE-Extensions				ProtocolExtensionContainer { {CriticalityDiagnostics-ExtIEs} }		OPTIONAL,
	...
}

CriticalityDiagnostics-ExtIEs NBAP-PROTOCOL-EXTENSION ::= {
	...
}

CriticalityDiagnostics-IE-List ::= SEQUENCE (SIZE (1..maxNrOfErrors)) OF
	SEQUENCE {
		iECriticality		Criticality,
		iE-ID				ProtocolIE-ID,
		repetitionNumber	RepetitionNumber0		OPTIONAL,
		iE-Extensions		ProtocolExtensionContainer { {CriticalityDiagnostics-IE-List-ExtIEs} }		OPTIONAL,
		...
	}

CriticalityDiagnostics-IE-List-ExtIEs NBAP-PROTOCOL-EXTENSION ::= {
	{	ID id-MessageStructure		CRITICALITY ignore		EXTENSION MessageStructure		PRESENCE optional	}|
	{	ID id-TypeOfError			CRITICALITY ignore		EXTENSION TypeOfError			PRESENCE mandatory	},
	...
}

CRNC-CommunicationContextID ::= INTEGER (0..1048575)

CSBMeasurementID ::= INTEGER (0..65535)

CSBTransmissionID ::= INTEGER (0..65535)

-- ==========================================
--	D
-- ==========================================

DATA-ID ::= INTEGER (0..3)

DCH-ID ::= INTEGER (0..255)

DCH-FDD-Information ::= SEQUENCE (SIZE (1..maxNrOfDCHs)) OF DCH-FDD-InformationItem

DCH-FDD-InformationItem ::= SEQUENCE {
	payloadCRC-PresenceIndicator		PayloadCRC-PresenceIndicator,
	ul-FP-Mode							UL-FP-Mode,
	toAWS								ToAWS,
	toAWE								ToAWE,
	dCH-SpecificInformationList			DCH-Specific-FDD-InformationList,
	iE-Extensions						ProtocolExtensionContainer { { DCH-FDD-InformationItem-ExtIEs} }	OPTIONAL,
	...
}

DCH-FDD-InformationItem-ExtIEs NBAP-PROTOCOL-EXTENSION ::= {
	...
}

DCH-Specific-FDD-InformationList ::= SEQUENCE (SIZE (1..maxNrOfDCHs)) OF DCH-Specific-FDD-Item

DCH-Specific-FDD-Item ::=	SEQUENCE {
	dCH-ID								DCH-ID,
	ul-TransportFormatSet				TransportFormatSet,
	dl-TransportFormatSet				TransportFormatSet,
	allocationRetentionPriority			AllocationRetentionPriority,
	frameHandlingPriority				FrameHandlingPriority,
	qE-Selector							QE-Selector,
	iE-Extensions						ProtocolExtensionContainer { { DCH-Specific-FDD-Item-ExtIEs} }	OPTIONAL,
	...
}

DCH-Specific-FDD-Item-ExtIEs NBAP-PROTOCOL-EXTENSION ::= {
	...
}

DCH-InformationResponse ::= SEQUENCE (SIZE (1..maxNrOfDCHs)) OF DCH-InformationResponseItem

DCH-InformationResponseItem ::= SEQUENCE {
	dCH-ID											DCH-ID,
	bindingID										BindingID				OPTIONAL,
	transportLayerAddress							TransportLayerAddress	OPTIONAL,
	iE-Extensions									ProtocolExtensionContainer { { DCH-InformationResponseItem-ExtIEs} }		OPTIONAL,
	...
}

DCH-InformationResponseItem-ExtIEs NBAP-PROTOCOL-EXTENSION ::= {
	...
}

DCH-TDD-Information ::= SEQUENCE (SIZE (1..maxNrOfDCHs)) OF DCH-TDD-InformationItem

DCH-TDD-InformationItem ::= SEQUENCE {
	payloadCRC-PresenceIndicator		PayloadCRC-PresenceIndicator,
	ul-FP-Mode							UL-FP-Mode,
	toAWS								ToAWS,
	toAWE								ToAWE,
	dCH-SpecificInformationList			DCH-Specific-TDD-InformationList,
	iE-Extensions							ProtocolExtensionContainer { { DCH-TDD-InformationItem-ExtIEs} }		OPTIONAL,
	...
}

DCH-TDD-InformationItem-ExtIEs NBAP-PROTOCOL-EXTENSION ::= {
	...
}

DCH-Specific-TDD-InformationList ::= SEQUENCE (SIZE (1..maxNrOfDCHs)) OF DCH-Specific-TDD-Item

DCH-Specific-TDD-Item ::=	SEQUENCE {
	dCH-ID									DCH-ID,
	ul-CCTrCH-ID							CCTrCH-ID,
	dl-CCTrCH-ID							CCTrCH-ID,
	ul-TransportFormatSet					TransportFormatSet,
	dl-TransportFormatSet					TransportFormatSet,
	allocationRetentionPriority				AllocationRetentionPriority,
	frameHandlingPriority					FrameHandlingPriority,
	qE-Selector								QE-Selector						OPTIONAL,
	-- This IE shall be present if DCH is part of set of Coordinated DCHs
	iE-Extensions							ProtocolExtensionContainer { { DCH-Specific-TDD-Item-ExtIEs} }		OPTIONAL,
	...
}

DCH-Specific-TDD-Item-ExtIEs NBAP-PROTOCOL-EXTENSION ::= {
	...
}

FDD-DCHs-to-Modify ::= SEQUENCE (SIZE (1..maxNrOfDCHs)) OF FDD-DCHs-to-ModifyItem

FDD-DCHs-to-ModifyItem	 ::= SEQUENCE {
	ul-FP-Mode							UL-FP-Mode		OPTIONAL,
	toAWS								ToAWS			OPTIONAL,
	toAWE								ToAWE			OPTIONAL,
	transportBearerRequestIndicator		TransportBearerRequestIndicator,
	dCH-SpecificInformationList			DCH-ModifySpecificInformation-FDD,
	iE-Extensions						ProtocolExtensionContainer { { FDD-DCHs-to-ModifyItem-ExtIEs} }		OPTIONAL,
	...
}

FDD-DCHs-to-ModifyItem-ExtIEs  NBAP-PROTOCOL-EXTENSION ::= {
	...
}

DCH-ModifySpecificInformation-FDD::= SEQUENCE (SIZE (1..maxNrOfDCHs)) OF DCH-ModifySpecificItem-FDD

DCH-ModifySpecificItem-FDD::=	SEQUENCE {
	dCH-ID											DCH-ID,
	ul-TransportFormatSet							TransportFormatSet			OPTIONAL,
	dl-TransportFormatSet							TransportFormatSet			OPTIONAL,
	allocationRetentionPriority						AllocationRetentionPriority	OPTIONAL,
	frameHandlingPriority							FrameHandlingPriority		OPTIONAL,
	iE-Extensions									ProtocolExtensionContainer { { DCH-ModifySpecificItem-FDD-ExtIEs} }		OPTIONAL,
	...
}

DCH-ModifySpecificItem-FDD-ExtIEs  NBAP-PROTOCOL-EXTENSION ::= {
	...
}


TDD-DCHs-to-Modify ::= SEQUENCE (SIZE (1..maxNrOfDCHs)) OF DCH-ModifyItem-TDD

DCH-ModifyItem-TDD ::= SEQUENCE {
	ul-FP-Mode							UL-FP-Mode		OPTIONAL,
	toAWS								ToAWS			OPTIONAL,
	toAWE								ToAWE			OPTIONAL,
	transportBearerRequestIndicator		TransportBearerRequestIndicator,
	dCH-SpecificInformationList			DCH-ModifySpecificInformation-TDD,
	iE-Extensions						ProtocolExtensionContainer { { TDD-DCHs-to-ModifyItem-ExtIEs} }			OPTIONAL,
	...
}

TDD-DCHs-to-ModifyItem-ExtIEs  NBAP-PROTOCOL-EXTENSION ::= {
	...
}

DCH-ModifySpecificInformation-TDD ::= SEQUENCE (SIZE (1..maxNrOfDCHs)) OF DCH-ModifySpecificItem-TDD

DCH-ModifySpecificItem-TDD ::=	SEQUENCE {
	dCH-ID											DCH-ID,
	ul-CCTrCH-ID									CCTrCH-ID					OPTIONAL,
	dl-CCTrCH-ID									CCTrCH-ID					OPTIONAL,
	ul-TransportFormatSet							TransportFormatSet			OPTIONAL,
	dl-TransportFormatSet							TransportFormatSet			OPTIONAL,
	allocationRetentionPriority						AllocationRetentionPriority	OPTIONAL,
	frameHandlingPriority							FrameHandlingPriority		OPTIONAL,
	iE-Extensions									ProtocolExtensionContainer { { DCH-ModifySpecificItem-TDD-ExtIEs} }			OPTIONAL,
	...
}

DCH-ModifySpecificItem-TDD-ExtIEs  NBAP-PROTOCOL-EXTENSION ::= {
	...
}

DedicatedChannelsCapacityConsumptionLaw ::= SEQUENCE ( SIZE(1..maxNrOfSF) ) OF
	SEQUENCE {
		dl-Cost-1		INTEGER (0..65535),
		dl-Cost-2		INTEGER (0..65535),
		ul-Cost-1		INTEGER (0..65535),
		ul-Cost-2		INTEGER (0..65535),
		iE-Extensions		ProtocolExtensionContainer { { DedicatedChannelsCapacityConsumptionLaw-ExtIEs } }		OPTIONAL,
	...
}

DedicatedChannelsCapacityConsumptionLaw-ExtIEs NBAP-PROTOCOL-EXTENSION ::= {
	...
}

DedicatedMeasurementType ::= ENUMERATED {
	sir,
	sir-error,
	transmitted-code-power,
	rscp,
	rx-timing-deviation,
	round-trip-time,
	...,
	rx-timing-deviation-LCR,
	angle-Of-Arrival-LCR
}

DedicatedMeasurementValue ::= CHOICE {
	sIR-Value						SIR-Value,
	sIR-ErrorValue					SIR-Error-Value,
	transmittedCodePowerValue			Transmitted-Code-Power-Value,
	rSCP								RSCP-Value,
	rxTimingDeviationValue				Rx-Timing-Deviation-Value,
	roundTripTime						Round-Trip-Time-Value,
	...,
	extension-DedicatedMeasurementValue		Extension-DedicatedMeasurementValue
}

Extension-DedicatedMeasurementValue	::= ProtocolIE-Single-Container {{ Extension-DedicatedMeasurementValueIE }}

Extension-DedicatedMeasurementValueIE NBAP-PROTOCOL-IES ::= {
	{ ID id-Rx-Timing-Deviation-Value-LCR	CRITICALITY reject	TYPE Rx-Timing-Deviation-Value-LCR	PRESENCE mandatory }|
	{ ID id-Angle-Of-Arrival-Value-LCR	CRITICALITY reject	TYPE Angle-Of-Arrival-Value-LCR	PRESENCE mandatory },
	...
}

DedicatedMeasurementValueInformation ::= CHOICE {
	measurementAvailable		DedicatedMeasurementAvailable,
	measurementnotAvailable		DedicatedMeasurementnotAvailable
}

DedicatedMeasurementAvailable::= SEQUENCE {
	dedicatedmeasurementValue		DedicatedMeasurementValue,
    cFN                             CFN							OPTIONAL,
	ie-Extensions					ProtocolExtensionContainer { { DedicatedMeasurementAvailableItem-ExtIEs} }		OPTIONAL,
	...
}

DedicatedMeasurementAvailableItem-ExtIEs NBAP-PROTOCOL-EXTENSION ::= {
	...
}

DedicatedMeasurementnotAvailable ::= NULL

DelayedActivation ::= CHOICE {
	cfn						CFN,
	separate-indication		NULL
}

DelayedActivationUpdate ::= CHOICE {
	activate		Activate-Info,
	deactivate		Deactivate-Info
}

Activate-Info ::= SEQUENCE {
	activation-type  		Execution-Type,
	initial-dl-tx-power 	DL-Power,
	firstRLS-Indicator		FirstRLS-Indicator											OPTIONAL, --FDD Only
	propagation-delay		PropagationDelay 											OPTIONAL, --FDD Only
	iE-Extensions			ProtocolExtensionContainer { { Activate-Info-ExtIEs} }		OPTIONAL,
	...
}

Activate-Info-ExtIEs NBAP-PROTOCOL-EXTENSION ::= {
	...
}

Deactivate-Info ::= SEQUENCE {
	deactivation-type  		Execution-Type,
	iE-Extensions			ProtocolExtensionContainer { { Deactivate-Info-ExtIEs} }		OPTIONAL,
	...
}

Deactivate-Info-ExtIEs NBAP-PROTOCOL-EXTENSION ::= {
	...
}

Execution-Type ::= CHOICE {
	synchronised 	CFN,
	unsynchronised	NULL
}

Detected-PCPCH-access-preambles ::= INTEGER (0..240,...)
-- According to mapping in [22].

DeltaSIR				::= INTEGER (0..30)
-- Unit dB, Step 0.1 dB, Range 0..3 dB.

DGPSCorrections ::= SEQUENCE {
   gpstow                GPSTOW,
   status-health         GPS-Status-Health,
   satelliteinfo         SAT-Info-DGPSCorrections,
   ie-Extensions		 ProtocolExtensionContainer { { DGPSCorrections-ExtIEs} }		OPTIONAL,
   ...
}

DGPSCorrections-ExtIEs NBAP-PROTOCOL-EXTENSION ::= {
	...
}

DGPSThresholds ::= SEQUENCE {
   prcdeviation         PRCDeviation,
   ie-Extensions		ProtocolExtensionContainer { { DGPSThresholds-ExtIEs} }		OPTIONAL,
   ...
}

DGPSThresholds-ExtIEs NBAP-PROTOCOL-EXTENSION ::= {
	...
}

DiversityControlField ::= ENUMERATED {
	may,
	must,
	must-not,
	...
}

DiversityMode ::= ENUMERATED {
	none, 
	sTTD,
	closed-loop-mode1,
	closed-loop-mode2,
	...
}

DL-DPCH-SlotFormat ::= INTEGER (0..16,...)

DL-DPCH-TimingAdjustment ::= ENUMERATED {
	timing-advance,
	timing-delay
}

DL-Timeslot-Information ::= SEQUENCE (SIZE (1.. maxNrOfDLTSs)) OF DL-Timeslot-InformationItem

DL-Timeslot-InformationItem	 ::= SEQUENCE {
	timeSlot								TimeSlot,
	midambleShiftAndBurstType				MidambleShiftAndBurstType,
	tFCI-Presence							TFCI-Presence,
	dL-Code-Information						TDD-DL-Code-Information,
	iE-Extensions							ProtocolExtensionContainer { { DL-Timeslot-InformationItem-ExtIEs} }		OPTIONAL,
	...
}

DL-Timeslot-InformationItem-ExtIEs NBAP-PROTOCOL-EXTENSION ::= {
	...
}

DL-TimeslotLCR-Information ::= SEQUENCE (SIZE (1.. maxNrOfDLTSLCRs)) OF DL-TimeslotLCR-InformationItem

DL-TimeslotLCR-InformationItem	 ::= SEQUENCE {
	timeSlotLCR								TimeSlotLCR,
	midambleShiftLCR						MidambleShiftLCR,
	tFCI-Presence							TFCI-Presence,
	dL-Code-LCR-Information					TDD-DL-Code-LCR-Information,
	iE-Extensions							ProtocolExtensionContainer { { DL-TimeslotLCR-InformationItem-ExtIEs} }		OPTIONAL,
	...
}

DL-TimeslotLCR-InformationItem-ExtIEs NBAP-PROTOCOL-EXTENSION ::= {
	...
}

DL-FrameType ::= ENUMERATED {
	typeA,
	typeB,
	...
}

DL-or-Global-CapacityCredit ::= INTEGER (0..65535)

DL-Power ::= INTEGER (-350..150)
-- Value = DL-Power/10
-- Unit dB, Range -35dB .. +15dB, Step +0.1dB

DLPowerAveragingWindowSize ::= INTEGER (1..60)

DL-PowerBalancing-Information ::= SEQUENCE {
	powerAdjustmentType					PowerAdjustmentType,
    dLReferencePower					DL-Power		OPTIONAL,
	-- This IE shall be present if Power Adjustment Type IE equals to 'Common'
	dLReferencePowerList-DL-PC-Rqst		DL-ReferencePowerInformationList		OPTIONAL,
	-- This IE shall be present if Power Adjustment Type IE equals to 'Individual'
	maxAdjustmentStep					MaxAdjustmentStep		OPTIONAL,
	-- This IE shall be present if Power Adjustment Type IE equals to 'Common' or 'Individual'
	adjustmentPeriod					AdjustmentPeriod		OPTIONAL,
	-- This IE shall be present if Power Adjustment Type IE equals to 'Common' or 'Individual'
	adjustmentRatio						ScaledAdjustmentRatio	OPTIONAL,
	-- This IE shall be present if Power Adjustment Type IE equals to 'Common' or 'Individual'
	iE-Extensions						ProtocolExtensionContainer { { DL-PowerBalancing-Information-ExtIEs } } OPTIONAL,
	...
}

DL-PowerBalancing-Information-ExtIEs NBAP-PROTOCOL-EXTENSION ::= {
	...
}

DL-ReferencePowerInformationList 		::= SEQUENCE (SIZE (1..maxNrOfRLs)) OF DL-ReferencePowerInformationItem

DL-ReferencePowerInformationItem ::= SEQUENCE {
	rL-ID						RL-ID,
	dl-Reference-Power			DL-Power,
	iE-Extensions				ProtocolExtensionContainer { {DL-ReferencePowerInformationItem-ExtIEs} } OPTIONAL,
	...
}

DL-ReferencePowerInformationItem-ExtIEs NBAP-PROTOCOL-EXTENSION ::= {
	...
}

DL-PowerBalancing-ActivationIndicator	::= ENUMERATED {
	dL-PowerBalancing-Activated
}

DL-PowerBalancing-UpdatedIndicator	::= ENUMERATED {
	dL-PowerBalancing-Updated
}

DL-ScramblingCode ::= INTEGER (0..15)
-- 0= Primary scrambling code of the cell, 1..15= Secondary scrambling code --

DL-TimeslotISCP ::= INTEGER (0..91)

DL-TimeslotISCPInfo ::= SEQUENCE (SIZE (1..maxNrOfDLTSs)) OF DL-TimeslotISCPInfoItem

DL-TimeslotISCPInfoItem ::= SEQUENCE {
	timeSlot					TimeSlot,
	dL-TimeslotISCP				DL-TimeslotISCP,
	iE-Extensions				ProtocolExtensionContainer { {DL-TimeslotISCPInfoItem-ExtIEs} }			OPTIONAL,
	...
	}

DL-TimeslotISCPInfoItem-ExtIEs  NBAP-PROTOCOL-EXTENSION ::= {
	...
}

DL-TimeslotISCPInfoLCR ::= SEQUENCE (SIZE (1..maxNrOfDLTSLCRs)) OF DL-TimeslotISCPInfoItemLCR

DL-TimeslotISCPInfoItemLCR ::= SEQUENCE {
	timeSlotLCR					TimeSlotLCR,
	dL-TimeslotISCP				DL-TimeslotISCP,
	iE-Extensions				ProtocolExtensionContainer { {DL-TimeslotISCPInfoItemLCR-ExtIEs} }			OPTIONAL,
	...
	}

DL-TimeslotISCPInfoItemLCR-ExtIEs  NBAP-PROTOCOL-EXTENSION ::= {
	...
}

DL-TPC-Pattern01Count ::= INTEGER (0..30,...)

Downlink-Compressed-Mode-Method 	::= ENUMERATED {
	puncturing,
	sFdiv2,
	higher-layer-scheduling,
	...
}

DPC-Mode ::= ENUMERATED {
	mode0,
	mode1,
	...
}

DPCH-ID ::= INTEGER (0..239)

DSCH-ID ::= INTEGER (0..255)

DSCH-InformationResponse ::= SEQUENCE (SIZE (1..maxNrOfDSCHs)) OF DSCH-InformationResponseItem

DSCH-InformationResponseItem ::= SEQUENCE {
	dSCH-ID											DSCH-ID,
	bindingID										BindingID					OPTIONAL,
	transportLayerAddress							TransportLayerAddress		OPTIONAL,
	iE-Extensions									ProtocolExtensionContainer { { DSCH-InformationResponseItem-ExtIEs } }		OPTIONAL,
	...
}

DSCH-InformationResponseItem-ExtIEs NBAP-PROTOCOL-EXTENSION ::= {
	...
}

DSCH-FDD-Common-Information ::= SEQUENCE {
	enhancedDSCHPCIndicator			EnhancedDSCHPCIndicator		OPTIONAL,
	enhancedDSCHPC					EnhancedDSCHPC				OPTIONAL,
	-- The IE shall be present if the Enhanced DSCH PC Indicator IE is set to "Enhanced DSCH PC Active in the UE".
	iE-Extensions						ProtocolExtensionContainer { { DSCH-FDD-Common-Information-ExtIEs} }		OPTIONAL,
	...
}

DSCH-FDD-Common-Information-ExtIEs NBAP-PROTOCOL-EXTENSION ::= {
	...
}

DSCH-FDD-Information ::= SEQUENCE (SIZE (1..maxNrOfDSCHs)) OF DSCH-FDD-InformationItem

DSCH-FDD-InformationItem ::= SEQUENCE {
	dSCH-ID								DSCH-ID,
	transportFormatSet					TransportFormatSet,
	allocationRetentionPriority			AllocationRetentionPriority,
	frameHandlingPriority				FrameHandlingPriority,
	toAWS								ToAWS,
	toAWE								ToAWE,
	iE-Extensions						ProtocolExtensionContainer { { DSCH-FDD-InformationItem-ExtIEs} }		OPTIONAL,
	...
}

DSCH-FDD-InformationItem-ExtIEs NBAP-PROTOCOL-EXTENSION ::= {
	{ ID id-bindingID						CRITICALITY	ignore		EXTENSION 	BindingID		PRESENCE 	optional	}|
	{ ID id-transportlayeraddress			CRITICALITY	ignore		EXTENSION 	TransportLayerAddress		PRESENCE 	optional	},
	...
}

DSCH-TDD-Information ::= SEQUENCE (SIZE (1..maxNrOfDSCHs)) OF DSCH-TDD-InformationItem

DSCH-TDD-InformationItem ::= SEQUENCE {
	dSCH-ID									DSCH-ID,
	cCTrCH-ID								CCTrCH-ID,
	transportFormatSet						TransportFormatSet,
	allocationRetentionPriority				AllocationRetentionPriority,
	frameHandlingPriority					FrameHandlingPriority,
	toAWS									ToAWS,
	toAWE									ToAWE,
	iE-Extensions							ProtocolExtensionContainer { { DSCH-TDD-InformationItem-ExtIEs} }		OPTIONAL,
	...
}

DSCH-TDD-InformationItem-ExtIEs NBAP-PROTOCOL-EXTENSION ::= {
	{ ID id-bindingID						CRITICALITY	ignore		EXTENSION 	BindingID		PRESENCE 	optional	}|
	{ ID id-transportlayeraddress			CRITICALITY	ignore		EXTENSION 	TransportLayerAddress		PRESENCE 	optional	},
	...
}

DwPCH-Power ::= ENUMERATED {minus10, minus9, minus8, minus7, minus6, minus5, minus4, minus3, minus2, minus1, zero, plus1, plus2, plus3, plus4, plus5, ...}

-- ==========================================
--	E
-- ==========================================

End-Of-Audit-Sequence-Indicator ::= INTEGER (-150..400,...)
-- DwPCH-power = power * 10
-- If power <= -15 DwPCH shall be set to -150
-- If power >= 40 DwPCH shall be set to 400
-- Unit dBm, Range -15dBm .. +40 dBm, Step +0.1dB

EnhancedDSCHPC ::= SEQUENCE {
	enhancedDSCHPCWnd 	EnhancedDSCHPCWnd,
	enhancedDSCHPCCounter 	EnhancedDSCHPCCounter,
	enhancedDSCHPowerOffset EnhancedDSCHPowerOffset,
	...
}

EnhancedDSCHPCCounter ::= INTEGER (1..50)

EnhancedDSCHPCIndicator ::= ENUMERATED {
	enhancedDSCHPCActiveInTheUE,
	enhancedDSCHPCNotActiveInTheUE
}

EnhancedDSCHPCWnd ::= INTEGER (1..10)

EnhancedDSCHPowerOffset ::= INTEGER (-15..0)

-- ==========================================
--	F
-- ==========================================

FDD-DL-ChannelisationCodeNumber ::= INTEGER(0.. 511)
-- According to the mapping in [9]. The maximum value is equal to the DL spreading factor -1--

FDD-DL-CodeInformation ::= SEQUENCE (SIZE (1..maxNrOfCodes)) OF FDD-DL-CodeInformationItem

FDD-DL-CodeInformationItem ::= SEQUENCE {
	dl-ScramblingCode						DL-ScramblingCode,
	fdd-DL-ChannelisationCodeNumber			FDD-DL-ChannelisationCodeNumber,
	transmissionGapPatternSequenceCodeInformation		TransmissionGapPatternSequenceCodeInformation		OPTIONAL,
	iE-Extensions							ProtocolExtensionContainer { { FDD-DL-CodeInformationItem-ExtIEs} }	OPTIONAL,
	...
}

FDD-DL-CodeInformationItem-ExtIEs NBAP-PROTOCOL-EXTENSION ::= {
	...
}

FDD-S-CCPCH-Offset ::= INTEGER (0..149)
-- 0: 0 chip, 1: 256 chip, 2: 512 chip, .. ,149: 38144 chip [7] --

FDD-TPC-DownlinkStepSize ::= ENUMERATED {
	step-size0-5,
	step-size1,
	step-size1-5,
	step-size2,
	...
}

FirstRLS-Indicator ::= ENUMERATED {
	first-RLS,
	not-first-RLS,
	...
}

FNReportingIndicator ::= ENUMERATED {
 fN-reporting-required,
 fN-reporting-not-required
}

FrameHandlingPriority ::= INTEGER (0..15)
-- 0=lower priority, 15=higher priority --

FrameAdjustmentValue ::= INTEGER(0..4095)

FrameOffset ::= INTEGER (0..255)

FPACH-Power ::= INTEGER (-150..400,...) -- FPACH-power = power * 10
-- If power <= -15 FPACH shall be set to -150
-- If power >= 40 FPACH shall be set to 400
-- Unit dBm, Range -15dBm .. +40 dBm, Step +0.1dB

-- ==========================================
--	G
-- ==========================================

GapLength				::= INTEGER (1..14)
-- Unit slot

GapDuration				::= INTEGER (1..144,...)
-- Unit frame

GPS-Almanac ::= SEQUENCE {
    wna-alm              BIT STRING (SIZE (8)),
     sat-info-almanac     SAT-Info-Almanac,
	sVGlobalHealth-alm	BIT STRING (SIZE (364))	OPTIONAL,
    ie-Extensions		 ProtocolExtensionContainer { { GPS-Almanac-ExtIEs} }		OPTIONAL,
   ...
}

GPS-Almanac-ExtIEs NBAP-PROTOCOL-EXTENSION ::= {
	...
}

GPS-Ionospheric-Model ::= SEQUENCE {
   alpha-zero-ionos      BIT STRING (SIZE (8)),
   alpha-one-ionos       BIT STRING (SIZE (8)),
   alpha-two-ionos       BIT STRING (SIZE (8)),
   alpha-three-ionos     BIT STRING (SIZE (8)),
   beta-zero-ionos       BIT STRING (SIZE (8)),
   beta-one-ionos        BIT STRING (SIZE (8)),
   beta-two-ionos        BIT STRING (SIZE (8)),
   beta-three-ionos      BIT STRING (SIZE (8)),
   ie-Extensions		 ProtocolExtensionContainer { { GPS-Ionospheric-Model-ExtIEs} }		OPTIONAL,
   ...
}

GPS-Ionospheric-Model-ExtIEs NBAP-PROTOCOL-EXTENSION ::= {
	...
}

GPS-Information ::= SEQUENCE (SIZE (0..maxNoGPSItems)) OF GPS-Information-Item
-- This IE shall be present if the Information Type Item IE indicates 'GPS Information'

GPS-Information-Item ::= ENUMERATED {
   gps-navigation-model-and-time-recovery,
   gps-ionospheric-model,
   gps-utc-model,
   gps-almanac,
   gps-rt-integrity,
   ...
}

GPS-RealTime-Integrity ::= CHOICE {
	bad-satellites		        GPSBadSat-Info-RealTime-Integrity,
	no-bad-satellites           NULL
}

GPSBadSat-Info-RealTime-Integrity ::= SEQUENCE {
	sat-info		                SATInfo-RealTime-Integrity,
	ie-Extensions					ProtocolExtensionContainer { { GPSBadSat-Info-RealTime-Integrity-ExtIEs} }		OPTIONAL,
	...
}

GPSBadSat-Info-RealTime-Integrity-ExtIEs NBAP-PROTOCOL-EXTENSION ::= {
	...
}

GPS-NavigationModel-and-TimeRecovery ::= SEQUENCE (SIZE (1..maxNoSat)) OF GPS-NavandRecovery-Item

GPS-NavandRecovery-Item ::= SEQUENCE {
  tx-tow-nav                       INTEGER (0..1048575),
  sat-id-nav                       SAT-ID,
  tlm-message-nav                  BIT STRING (SIZE (14)),
  tlm-revd-c-nav                   BIT STRING (SIZE (2)),
  ho-word-nav                      BIT STRING (SIZE (22)),
  w-n-nav                          BIT STRING (SIZE (10)),
  ca-or-p-on-l2-nav                BIT STRING (SIZE (2)),
  user-range-accuracy-index-nav    BIT STRING (SIZE (4)),
  sv-health-nav                    BIT STRING (SIZE (6)),
  iodc-nav                         BIT STRING (SIZE (10)),
  l2-p-dataflag-nav                BIT STRING (SIZE (1)),
  sf1-reserved-nav                 BIT STRING (SIZE (87)),
  t-gd-nav                         BIT STRING (SIZE (8)),
  t-oc-nav                         BIT STRING (SIZE (16)),
  a-f-2-nav                        BIT STRING (SIZE (8)),
  a-f-1-nav                        BIT STRING (SIZE (16)),
  a-f-zero-nav                     BIT STRING (SIZE (22)),
  c-rs-nav                         BIT STRING (SIZE (16)),
  delta-n-nav                      BIT STRING (SIZE (16)),
  m-zero-nav                       BIT STRING (SIZE (32)),
  c-uc-nav                         BIT STRING (SIZE (16)),
  gps-e-nav                        BIT STRING (SIZE (32)),
  c-us-nav                         BIT STRING (SIZE (16)),
  a-sqrt-nav                       BIT STRING (SIZE (32)),
  t-oe-nav                         BIT STRING (SIZE (16)),
  fit-interval-flag-nav            BIT STRING (SIZE (1)),
  aodo-nav                         BIT STRING (SIZE (5)),
  c-ic-nav                         BIT STRING (SIZE (16)),
  omega-zero-nav                   BIT STRING (SIZE (32)),
  c-is-nav                         BIT STRING (SIZE (16)),
  i-zero-nav                       BIT STRING (SIZE (32)),
  c-rc-nav                         BIT STRING (SIZE (16)),
  gps-omega-nav                    BIT STRING (SIZE (32)),
  omegadot-nav                     BIT STRING (SIZE (24)),
  idot-nav                         BIT STRING (SIZE (14)),
  spare-zero-fill                  BIT STRING (SIZE (20)),
  ie-Extensions		               ProtocolExtensionContainer { { GPS-NavandRecovery-Item-ExtIEs} }		OPTIONAL,
   ...
}

GPS-NavandRecovery-Item-ExtIEs NBAP-PROTOCOL-EXTENSION ::= {
	...
}


GPS-RX-POS ::= SEQUENCE {
    latitudeSign		    ENUMERATED {north, south},
	latitude			    INTEGER (0..8388607),
	longitude			    INTEGER (-8388608..8388607),
	directionOfAltitude		ENUMERATED {height, depth},
	altitude				INTEGER (0..32767),
	iE-Extensions			ProtocolExtensionContainer { { GPS-RX-POS-ExtIEs} } OPTIONAL,
	...
}

GPS-RX-POS-ExtIEs NBAP-PROTOCOL-EXTENSION ::= {
	...
}

GPS-Status-Health ::= ENUMERATED {
   udre-scale-1dot0,
   udre-scale-0dot75,
   udre-scale-0dot5,
   udre-scale-0dot3,
   udre-scale-0dot1,
   no-data,
   invalid-data
}

GPSTOW ::= INTEGER (0..604799)

GPS-UTC-Model ::= SEQUENCE {
   a-one-utc             BIT STRING (SIZE (24)),
   a-zero-utc            BIT STRING (SIZE (32)),
   t-ot-utc              BIT STRING (SIZE (8)),
   delta-t-ls-utc        BIT STRING (SIZE (8)),
   w-n-t-utc             BIT STRING (SIZE (8)),
   w-n-lsf-utc           BIT STRING (SIZE (8)),
   dn-utc                BIT STRING (SIZE (8)),
   delta-t-lsf-utc       BIT STRING (SIZE (8)),
   ie-Extensions		 ProtocolExtensionContainer { { GPS-UTC-Model-ExtIEs} }		OPTIONAL,
   ...
}

GPS-UTC-Model-ExtIEs NBAP-PROTOCOL-EXTENSION ::= {
	...
}

-- ==========================================
--	H
-- ==========================================

HARQMemoryPartitioningFDD ::= SEQUENCE (SIZE (1..maxNrOfHARQProcesses)) OF HARQMemoryPartitioning-ItemFDD

HARQMemoryPartitioning-ItemFDD ::= SEQUENCE {
	process-Memory-Size					INTEGER (0..172800,...),
	iE-Extensions						ProtocolExtensionContainer { { HARQMemoryPartitioning-ItemFDD-ExtIEs} }		OPTIONAL,
	...
}

HARQMemoryPartitioning-ItemFDD-ExtIEs NBAP-PROTOCOL-EXTENSION ::= {
	...
}

HARQMemoryPartitioningTDD ::= SEQUENCE (SIZE (1..maxNrOfHARQProcesses)) OF HARQMemoryPartitioning-ItemTDD

HARQMemoryPartitioning-ItemTDD ::= SEQUENCE {
	process-Memory-Size					INTEGER (0..168960,...),
	iE-Extensions						ProtocolExtensionContainer { { HARQMemoryPartitioning-ItemTDD-ExtIEs} }		OPTIONAL,
	...
}

HARQMemoryPartitioning-ItemTDD-ExtIEs NBAP-PROTOCOL-EXTENSION ::= {
	...
}

HSDSCH-FDD-Information ::= SEQUENCE {
	hsDSCH-MACdFlow-Specific-Info		HSDSCH-MACdFlow-Specific-InfoList,
	ueCapability-Info					UE-Capability-InformationFDD,
	harqMemoryPartitioningFDD			HARQMemoryPartitioningFDD,
	cqiFeedback-CycleK					CQI-Feedback-Cycle,
	cqiRepetitionFactor					CQI-RepetitionFactor			OPTIONAL,
	-- This IE shall be present if the CQI Feedback Cycle k is greater than 0
	ackNackRepetitionFactor				AckNack-RepetitionFactor,
	cqiPowerOffset						CQI-Power-Offset,
	ackPowerOffset						Ack-Power-Offset,
	nackPowerOffset						Nack-Power-Offset,
	hsscch-PowerOffset					HSSCCH-PowerOffset				OPTIONAL,
	measurement-Power-Offset			Measurement-Power-Offset		OPTIONAL,
	iE-Extensions						ProtocolExtensionContainer { { HSDSCH-FDD-Information-ExtIEs} }		OPTIONAL,
	...
}

HSDSCH-FDD-Information-ExtIEs NBAP-PROTOCOL-EXTENSION ::= {
	...
}

HSDSCH-TDD-Information ::= SEQUENCE {
	hsDSCH-MACdFlow-Specific-Info		HSDSCH-MACdFlow-Specific-InfoList,
	ueCapability-Info					UE-Capability-InformationTDD,
	harqMemoryPartitioningTDD			HARQMemoryPartitioningTDD,
	iE-Extensions						ProtocolExtensionContainer { { HSDSCH-TDD-Information-ExtIEs} }		OPTIONAL,
	...
}

HSDSCH-TDD-Information-ExtIEs NBAP-PROTOCOL-EXTENSION ::= {
	...
}

HSDSCH-MACdFlow-Specific-InfoList ::= SEQUENCE (SIZE (1..maxNrOfMACdFlows)) OF HSDSCH-MACdFlow-Specific-InfoItem

HSDSCH-MACdFlow-Specific-InfoItem ::= SEQUENCE {
	hsDSCH-MACdFlow-ID					HSDSCH-MACdFlow-ID,
	allocationRetentionPriority			AllocationRetentionPriority,
	bindingID							BindingID					OPTIONAL,
	transportLayerAddress				TransportLayerAddress		OPTIONAL,
	priorityQueueInfo					PriorityQueue-InfoList,
	iE-Extensions						ProtocolExtensionContainer { { HSDSCH-MACdFlow-Specific-InfoItem-ExtIEs} }		OPTIONAL,
	...
}

HSDSCH-MACdFlow-Specific-InfoItem-ExtIEs NBAP-PROTOCOL-EXTENSION ::= {
	...
}

HSDSCH-Information-to-Modify ::= SEQUENCE {
	hsDSCH-MACdFlow-Specific-Info-to-Modify			HSDSCH-MACdFlow-Specific-InfoList-to-Modify		OPTIONAL,
	cqiFeedback-CycleK								CQI-Feedback-Cycle				OPTIONAL,	-- For FDD only
	cqiRepetitionFactor								CQI-RepetitionFactor			OPTIONAL,	-- For FDD only
	ackNackRepetitionFactor							AckNack-RepetitionFactor		OPTIONAL,	-- For FDD only
	cqiPowerOffset									CQI-Power-Offset				OPTIONAL,	-- For FDD only
	ackPowerOffset									Ack-Power-Offset				OPTIONAL,	-- For FDD only
	nackPowerOffset									Nack-Power-Offset				OPTIONAL,	-- For FDD only
	hsscch-PowerOffset								HSSCCH-PowerOffset				OPTIONAL, -- only for FDD
	measurement-Power-Offset						Measurement-Power-Offset		OPTIONAL,	-- For FDD only
	iE-Extensions									ProtocolExtensionContainer { { HSDSCH-Information-to-Modify-ExtIEs} }		OPTIONAL,
	...
}

HSDSCH-Information-to-Modify-ExtIEs NBAP-PROTOCOL-EXTENSION ::= {
	...
}

HSDSCH-MACdFlow-Specific-InfoList-to-Modify ::= SEQUENCE (SIZE (1..maxNrOfMACdFlows)) OF HSDSCH-MACdFlow-Specific-InfoItem-to-Modify

HSDSCH-MACdFlow-Specific-InfoItem-to-Modify ::= SEQUENCE {
	hsDSCH-MACdFlow-ID					HSDSCH-MACdFlow-ID,
	allocationRetentionPriority			AllocationRetentionPriority					OPTIONAL,
	transportBearerRequestIndicator		TransportBearerRequestIndicator,
	bindingID							BindingID									OPTIONAL,
	transportLayerAddress				TransportLayerAddress						OPTIONAL,
	priorityQueueInfotoModify			PriorityQueue-InfoList-to-Modify			OPTIONAL,
	iE-Extensions						ProtocolExtensionContainer { { HSDSCH-MACdFlow-Specific-InfoItem-to-Modify-ExtIEs} }		OPTIONAL,
	...
}

HSDSCH-MACdFlow-Specific-InfoItem-to-Modify-ExtIEs NBAP-PROTOCOL-EXTENSION ::= {
	...
}

HSDSCH-FDD-Information-Response ::= SEQUENCE {
	hsDSCH-MACdFlow-Specific-InformationResp		HSDSCH-MACdFlow-Specific-InformationResp,
	hsSCCH-Specific-Information-ResponseFDD			HSSCCH-Specific-InformationRespListFDD,
	iE-Extensions									ProtocolExtensionContainer { { HSDSCH-FDD-Information-Response-ExtIEs } }		OPTIONAL,
	...
}

HSDSCH-FDD-Information-Response-ExtIEs NBAP-PROTOCOL-EXTENSION ::= {
	...
}

HSDSCH-TDD-Information-Response ::= SEQUENCE {
	hsDSCH-MACdFlow-Specific-InformationResp		HSDSCH-MACdFlow-Specific-InformationResp,
	hsSCCH-Specific-Information-ResponseTDD			HSSCCH-Specific-InformationRespListTDD			OPTIONAL,
	hsSCCH-Specific-Information-ResponseTDDLCR		HSSCCH-Specific-InformationRespListTDDLCR		OPTIONAL,
	iE-Extensions									ProtocolExtensionContainer { { HSDSCH-TDD-Information-Response-ExtIEs } }		OPTIONAL,
	...
}

HSDSCH-TDD-Information-Response-ExtIEs NBAP-PROTOCOL-EXTENSION ::= {
	...
}

HSDSCH-MACdFlow-Specific-InformationResp ::= SEQUENCE (SIZE (1..maxNrOfMACdFlows)) OF HSDSCH-MACdFlow-Specific-InformationResp-Item

HSDSCH-MACdFlow-Specific-InformationResp-Item ::= SEQUENCE {
	hsDSCHMacdFlow-Id								HSDSCH-MACdFlow-ID,
	bindingID										BindingID					OPTIONAL,
	transportLayerAddress							TransportLayerAddress		OPTIONAL,
	hSDSCH-Initial-Capacity-Allocation				HSDSCH-Initial-Capacity-Allocation OPTIONAL,
	iE-Extensions									ProtocolExtensionContainer { { HSDSCH-MACdFlow-Specific-InformationRespItem-ExtIEs } }		OPTIONAL,
	...
}

HSDSCH-MACdFlow-Specific-InformationRespItem-ExtIEs NBAP-PROTOCOL-EXTENSION ::= {
	...
}

HSSCCH-PowerOffset ::= INTEGER (0..255)
-- PowerOffset = -32 + offset * 0.25
-- Unit dB, Range -32dB .. +31.75dB, Step +0.25dB

HSDSCH-Initial-Capacity-Allocation::= SEQUENCE (SIZE (1..16)) OF HSDSCH-Initial-Capacity-AllocationItem

HSDSCH-Initial-Capacity-AllocationItem ::= SEQUENCE {
	schedulingPriorityIndicator		SchedulingPriorityIndicator,
	maximum-MACdPDU-Size			MACdPDU-Size,
	hSDSCH-InitialWindowSize		HSDSCH-InitialWindowSize,
	iE-Extensions					ProtocolExtensionContainer { { HSDSCH-Initial-Capacity-AllocationItem-ExtIEs } } OPTIONAL,
	...
}

HSDSCH-Initial-Capacity-AllocationItem-ExtIEs NBAP-PROTOCOL-EXTENSION ::= {
	...
}

HSDSCH-InitialWindowSize			::= INTEGER (1..2047)
-- Number of MAC-d PDUs.
-- 2047 = Unlimited number of MAC-d PDUs

HSSCCH-Specific-InformationRespListFDD ::= SEQUENCE (SIZE (1..maxNrOfHSSCCHCodes)) OF HSSCCH-Codes

HSSCCH-Codes ::= SEQUENCE {
	codeNumber										INTEGER (1..127),
	iE-Extensions									ProtocolExtensionContainer { { HSSCCH-Specific-InformationRespItemFDD-ExtIEs } }		OPTIONAL,
	...
}

HSSCCH-Specific-InformationRespItemFDD-ExtIEs NBAP-PROTOCOL-EXTENSION ::= {
	...
}

HSSCCH-Specific-InformationRespListTDD ::= SEQUENCE (SIZE (1..maxNrOfHSSCCHCodes)) OF HSSCCH-Specific-InformationRespItemTDD

HSSCCH-Specific-InformationRespItemTDD ::= SEQUENCE {
	timeslot										TimeSlot,
	midambleShiftAndBurstType						MidambleShiftAndBurstType,
	tDD-ChannelisationCode							TDD-ChannelisationCode,
	hSSICH-Info										HSSICH-Info,
	iE-Extensions									ProtocolExtensionContainer { { HSSCCH-Specific-InformationRespItemTDD-ExtIEs } }			OPTIONAL,
	...
}

HSSCCH-Specific-InformationRespItemTDD-ExtIEs NBAP-PROTOCOL-EXTENSION ::= {
	...
}

HSSCCH-Specific-InformationRespListTDDLCR ::= SEQUENCE (SIZE (1..maxNrOfHSSCCHCodes)) OF HSSCCH-Specific-InformationRespItemTDDLCR

HSSCCH-Specific-InformationRespItemTDDLCR ::= SEQUENCE {
	timeslotLCR									TimeSlotLCR,
	midambleShiftLCR							MidambleShiftLCR,
	first-TDD-ChannelisationCodeLCR					TDD-ChannelisationCodeLCR,
	second-TDD-ChannelisationCodeLCR			TDD-ChannelisationCodeLCR,
	hSSICH-InfoLCR								HSSICH-InfoLCR,
	iE-Extensions								ProtocolExtensionContainer { { HSSCCH-Specific-InformationRespItemTDDLCR-ExtIEs } }			OPTIONAL,
	...
}

HSSCCH-Specific-InformationRespItemTDDLCR-ExtIEs NBAP-PROTOCOL-EXTENSION ::= {
	...
}

HSSICH-Info ::= SEQUENCE {
	timeslot										TimeSlot,
	midambleShiftAndBurstType						MidambleShiftAndBurstType,
	tDD-ChannelisationCode							TDD-ChannelisationCode,
	iE-Extensions									ProtocolExtensionContainer { { HSSICH-Info-ExtIEs } }			OPTIONAL,
	...
}

HSSICH-Info-ExtIEs NBAP-PROTOCOL-EXTENSION ::= {
	...
}

HSSICH-InfoLCR ::= SEQUENCE {
	timeslotLCR										TimeSlotLCR,
	midambleShiftLCR								MidambleShiftLCR,
	tDD-ChannelisationCodeLCR						TDD-ChannelisationCodeLCR,
	iE-Extensions									ProtocolExtensionContainer { { HSSICH-Info-LCR-ExtIEs } }			OPTIONAL,
	...
}

HSSICH-Info-LCR-ExtIEs NBAP-PROTOCOL-EXTENSION ::= {
	...
}

HSDSCH-MACdFlow-ID ::= INTEGER (0..maxNrOfMACdFlows-1)

HSDSCH-RNTI ::= INTEGER (0..65535)

HS-PDSCH-FDD-Code-Information ::= SEQUENCE {
   number-of-HS-PDSCH-codes						INTEGER (0..maxCodeNrComp-1),
   hS-PDSCH-Start-code-number 					HS-PDSCH-Start-code-number		OPTIONAL, 
-- Only included when number of HS-DSCH codes > 0
   ...
}

HS-PDSCH-Start-code-number ::=	INTEGER (0..maxCodeNrComp-1)

HS-SCCH-ID ::= INTEGER (0..31)

HS-SCCH-FDD-Code-Information::= CHOICE {
	replace					HS-SCCH-FDD-Code-List,
	remove					NULL,
	...
}

HS-SCCH-FDD-Code-List ::= SEQUENCE (SIZE (1..maxNrOfHSSCCHs)) OF HS-SCCH-FDD-Code-Information-Item

HS-SCCH-FDD-Code-Information-Item ::= INTEGER (0..maxCodeNrComp-1)

HSSCCH-CodeChangeIndicator	::= ENUMERATED {
	hsSCCHCodeChangeNeeded
}

HSDSCH-FDD-Update-Information ::= SEQUENCE {
	hsSCCHCodeChangeIndicator						HSSCCH-CodeChangeIndicator					OPTIONAL,
	cqiFeedback-CycleK								CQI-Feedback-Cycle							OPTIONAL, 
	cqiRepetitionFactor								CQI-RepetitionFactor						OPTIONAL,
	ackNackRepetitionFactor							AckNack-RepetitionFactor					OPTIONAL,
	cqiPowerOffset									CQI-Power-Offset 							OPTIONAL,
	ackPowerOffset									Ack-Power-Offset							OPTIONAL,
	nackPowerOffset									Nack-Power-Offset							OPTIONAL,
	iE-Extensions									ProtocolExtensionContainer { { HSDSCH-FDD-Update-Information-ExtIEs } }		OPTIONAL,
	...
}

HSDSCH-FDD-Update-Information-ExtIEs NBAP-PROTOCOL-EXTENSION ::= {
	...
}

HSDSCH-TDD-Update-Information ::= SEQUENCE {
	hsSCCHCodeChangeIndicator						HSSCCH-CodeChangeIndicator					OPTIONAL,
	iE-Extensions									ProtocolExtensionContainer { { HSDSCH-TDD-Update-Information-ExtIEs } }		OPTIONAL,
	...
}

HSDSCH-TDD-Update-Information-ExtIEs NBAP-PROTOCOL-EXTENSION ::= {
	...
}

-- ==========================================
--	I
-- ==========================================

IB-OC-ID ::= INTEGER (1..16)

IB-SG-DATA ::= BIT STRING
-- Contains SIB data fixed" or "SIB data variable" in segment as encoded in ref.[18].

IB-SG-POS ::= INTEGER (0..4094)
-- Only even positions allowed

IB-SG-REP ::= ENUMERATED {rep4, rep8, rep16, rep32, rep64, rep128, rep256, rep512, rep1024, rep2048, rep4096}

IB-Type ::= ENUMERATED {
	mIB, 
	sB1,
	sB2,
	sIB1, 
	sIB2,
	sIB3,
	sIB4,
	sIB5,
	sIB6,
	sIB7,
	sIB8,
	sIB9,
	sIB10,
	sIB11,
	sIB12,
	sIB13,
	sIB13dot1,
	sIB13dot2,
	sIB13dot3,
	sIB13dot4,
	sIB14,
	sIB15,
	sIB15dot1,
	sIB15dot2,
	sIB15dot3,
	sIB16,
	...,
	sIB17,
	sIB15dot4,
	sIB18,
	sIB15dot5
}

InformationReportCharacteristics ::= CHOICE {
	onDemand				NULL,
	periodic				InformationReportCharacteristicsType-ReportPeriodicity,
	onModification          InformationReportCharacteristicsType-OnModification,
	...
}

InformationReportCharacteristicsType-ReportPeriodicity ::= CHOICE {
	min 				ReportPeriodicity-Scaledmin,
	hours				ReportPeriodicity-Scaledhour,
	...
}

InformationReportCharacteristicsType-OnModification ::= SEQUENCE {
    information-thresholds        InformationThresholds		OPTIONAL,
    ie-Extensions		          ProtocolExtensionContainer { { InformationReportCharacteristicsType-OnModification-ExtIEs} }	OPTIONAL,
   ...
}

InformationReportCharacteristicsType-OnModification-ExtIEs NBAP-PROTOCOL-EXTENSION ::= {
	...
}

InformationThresholds ::= CHOICE {
    dgps                DGPSThresholds,
   	...
} 

InformationExchangeID ::= INTEGER (0..1048575)

InformationType ::= SEQUENCE {
	information-Type-Item		Information-Type-Item,
	gPSInformation  			GPS-Information  OPTIONAL,
	-- The IE shall be present if the Information Type Item IE indicates "GPS Information".
	iE-Extensions				ProtocolExtensionContainer { { Information-Type-ExtIEs} }		OPTIONAL,
...
}

Information-Type-ExtIEs NBAP-PROTOCOL-EXTENSION ::= {
	...
}

Information-Type-Item ::= ENUMERATED {
    gpsinformation,
    dgpscorrections,
    gpsrxpos,
    ...
}

InnerLoopDLPCStatus ::= ENUMERATED {
	active,
	inactive
}

IPDL-Indicator ::= ENUMERATED {
	active,
	inactive
}


IPDL-FDD-Parameters ::= SEQUENCE {
	iP-SpacingFDD					ENUMERATED{sp5,sp7,sp10,sp15,sp20,sp30,sp40,sp50,...},
	iP-Length						ENUMERATED{len5, len10},
	seed							INTEGER(0..63),
	burstModeParams					BurstModeParams		OPTIONAL,
	iP-Offset						INTEGER(0..9),
	iE-Extensions					ProtocolExtensionContainer { { IPDLFDDParameter-ExtIEs} }	OPTIONAL,
	...
}

IPDLFDDParameter-ExtIEs NBAP-PROTOCOL-EXTENSION ::= {
	...
}

IPDL-TDD-Parameters ::= SEQUENCE {
	iP-SpacingTDD					ENUMERATED{sp30,sp40,sp50,sp70,sp100,...},
	iP-Start						INTEGER(0..4095),
	iP-Slot							INTEGER(0..14),
	iP-PCCPCH						ENUMERATED{switchOff-1-Frame,switchOff-2-Frames},
	burstModeParams					BurstModeParams		OPTIONAL,
	iE-Extensions			ProtocolExtensionContainer { { IPDLTDDParameter-ExtIEs} }	OPTIONAL,
	...
}

IPDL-TDD-Parameters-LCR ::= SEQUENCE {
	iP-SpacingTDD					ENUMERATED{sp30,sp40,sp50,sp70,sp100,...},
	iP-Start						INTEGER(0..4095),
	iP-Sub							ENUMERATED{first,second,both},
	burstModeParams					BurstModeParams		OPTIONAL,
	iE-Extensions			ProtocolExtensionContainer { { IPDLTDDParameterLCR-ExtIEs} }	OPTIONAL,
	...
}

BurstModeParams ::= SEQUENCE {
	burstStart							INTEGER(0..15),
	burstLenth							INTEGER(10..25),
	burstFreq							INTEGER(1..16),
	...
}

IPDLTDDParameter-ExtIEs NBAP-PROTOCOL-EXTENSION ::= {
	...
}

IPDLTDDParameterLCR-ExtIEs NBAP-PROTOCOL-EXTENSION ::= {
	...
}

-- ==========================================
--	J
-- ==========================================

-- ==========================================
--	K
-- ==========================================

-- ==========================================
--	L
-- ==========================================

LimitedPowerIncrease ::= ENUMERATED {
	used,
	not-used
}

Local-Cell-ID ::= INTEGER (0..268435455)

-- ==========================================
--	M
-- ==========================================

MACdPDU-Size ::= INTEGER (1..5000,...)

MACdPDU-Size-Indexlist ::= SEQUENCE (SIZE (1..maxNrOfMACdPDUIndexes)) OF MACdPDU-Size-IndexItem

MACdPDU-Size-IndexItem ::= SEQUENCE {
	sID									INTEGER (0..7),
	macdPDU-Size						MACdPDU-Size,
	iE-Extensions						ProtocolExtensionContainer { { MACdPDU-Size-IndexItem-ExtIEs} }		OPTIONAL,
	...
}

MACdPDU-Size-IndexItem-ExtIEs NBAP-PROTOCOL-EXTENSION ::= {
	...
}

MACdPDU-Size-Indexlist-to-Modify ::= SEQUENCE (SIZE (1..maxNrOfMACdPDUIndexes)) OF MACdPDU-Size-IndexItem-to-Modify

MACdPDU-Size-IndexItem-to-Modify ::= SEQUENCE {
	sID									INTEGER (0..7),
	macdPDU-Size						MACdPDU-Size												OPTIONAL,
	iE-Extensions						ProtocolExtensionContainer { { MACdPDU-Size-IndexItem-to-Modify-ExtIEs} }		OPTIONAL,
	...
}

MACdPDU-Size-IndexItem-to-Modify-ExtIEs NBAP-PROTOCOL-EXTENSION ::= {
	...
}

MAC-hsWindowSize		::= ENUMERATED {v4, v6, v8, v12, v16, v24, v32,...}

MaximumDL-PowerCapability ::=  INTEGER(0..500)
-- Unit dBm, Range 0dBm .. 50dBm, Step +0.1dB

Maximum-PDSCH-Power ::= SEQUENCE {
	maximum-PDSCH-Power-SF4		DL-Power		OPTIONAL,
	maximum-PDSCH-Power-SF8		DL-Power		OPTIONAL,
	maximum-PDSCH-Power-SF16	DL-Power		OPTIONAL,
	maximum-PDSCH-Power-SF32	DL-Power		OPTIONAL,
	maximum-PDSCH-Power-SF64	DL-Power		OPTIONAL,
	maximum-PDSCH-Power-SF128	DL-Power		OPTIONAL,
	maximum-PDSCH-Power-SF256	DL-Power		OPTIONAL,
	iE-Extensions			ProtocolExtensionContainer { { Maximum-PDSCH-Power-ExtIEs} }		OPTIONAL,
	...
}

Maximum-PDSCH-Power-ExtIEs NBAP-PROTOCOL-EXTENSION ::= {
	...
}

MaximumTransmissionPower ::=  INTEGER(0..500)
-- Unit dBm, Range 0dBm .. 50dBm, Step +0.1dB

MaxNrOfUL-DPDCHs ::= INTEGER (1..6)

Max-Number-of-PCPCHes ::= INTEGER (1..64,...)

MaxPRACH-MidambleShifts ::= ENUMERATED {
	shift4,
	shift8,
	...
}

MeasurementFilterCoefficient ::= ENUMERATED {k0, k1, k2, k3, k4, k5, k6, k7, k8, k9, k11, k13, k15, k17, k19,...}
-- Measurement Filter Coefficient to be used for measurement

MeasurementID ::= INTEGER (0..1048575)

Measurement-Power-Offset ::= INTEGER(-12 .. 26)
-- Actual value = IE value * 0.5

MessageStructure ::= SEQUENCE (SIZE (1..maxNrOfLevels)) OF
	SEQUENCE { 
		iE-ID					ProtocolIE-ID,
		repetitionNumber		RepetitionNumber1		OPTIONAL,
		iE-Extensions			ProtocolExtensionContainer { {MessageStructure-ExtIEs} } OPTIONAL,
		...
	}

MessageStructure-ExtIEs NBAP-PROTOCOL-EXTENSION ::= {
	...
}

MidambleConfigurationBurstType1And3 ::=		ENUMERATED {v4, v8, v16}

MidambleConfigurationBurstType2 ::=		ENUMERATED {v3, v6}

MidambleShiftAndBurstType ::=		CHOICE {	
	type1								SEQUENCE {
		midambleConfigurationBurstType1And3	MidambleConfigurationBurstType1And3,
		midambleAllocationMode 				CHOICE {
			defaultMidamble						NULL,
			commonMidamble						NULL,
			ueSpecificMidamble					MidambleShiftLong,
			...
		},
	...
	},
	type2								SEQUENCE {
		midambleConfigurationBurstType2		MidambleConfigurationBurstType2,
		midambleAllocationMode 				CHOICE {
			defaultMidamble						NULL,
			commonMidamble						NULL,
			ueSpecificMidamble					MidambleShiftShort,
			...
		},
		...
	},
	type3								SEQUENCE {
		midambleConfigurationBurstType1And3	MidambleConfigurationBurstType1And3,
		midambleAllocationMode 				CHOICE {
			defaultMidamble						NULL,
			ueSpecificMidamble					MidambleShiftLong,
		...
		},
		...
	},
	...
}

MidambleShiftLong ::=				INTEGER (0..15)

MidambleShiftShort ::=				INTEGER (0..5)

MidambleShiftLCR ::= SEQUENCE {
	midambleAllocationMode		MidambleAllocationMode,
	midambleShift				MidambleShiftLong		OPTIONAL,
	-- The IE shall be present if the Midamble Allocation Mode IE is set to "UE specific midamble".
	iE-Extensions				ProtocolExtensionContainer { {MidambleShiftLCR-ExtIEs} }		OPTIONAL,
	...
	}

MidambleAllocationMode ::= ENUMERATED {
	defaultMidamble,
	commonMidamble,
	uESpecificMidamble, 
	...
	}

MidambleShiftLCR-ExtIEs  NBAP-PROTOCOL-EXTENSION ::= {
	...
}

MinimumDL-PowerCapability ::=  INTEGER(0..800)
-- Unit dBm, Range -30dBm .. 50dBm, Step +0.1dB

MinSpreadingFactor ::= ENUMERATED {
		v4,
		v8,
		v16,
		v32,
		v64,
		v128,
		v256,
		v512
}
--  TDD Mapping scheme for the minimum spreading factor 1 and 2: "256" means 1, "512" means 2

Modulation ::= ENUMERATED {
	qPSK,
	eightPSK,
	...
}

MinUL-ChannelisationCodeLength ::= ENUMERATED {
	v4,
	v8,
	v16,
	v32,
	v64,
	v128,
	v256,
	...
}

MultiplexingPosition ::= ENUMERATED {
	fixed,
	flexible
}

-- ==========================================
--	N
-- ==========================================

Nack-Power-Offset ::= INTEGER (0..8,...)
-- According to mapping in ref. [9] subclause 4.2.1

NCyclesPerSFNperiod ::= ENUMERATED {
	v1,
	v2,
	v4,
	v8,
	...,
	v16,
	v32,
	v64
}

NEOT ::= INTEGER (0..8)

NFmax ::= INTEGER (1..64,...)

NRepetitionsPerCyclePeriod ::= INTEGER (2..10)

N-INSYNC-IND ::= INTEGER (1..256)

N-OUTSYNC-IND ::= INTEGER (1..256)

NeighbouringCellMeasurementInformation ::= SEQUENCE (SIZE (1..maxNrOfMeasNCell)) OF
		CHOICE {
				neighbouringFDDCellMeasurementInformation		NeighbouringFDDCellMeasurementInformation, -- FDD only
				neighbouringTDDCellMeasurementInformation		NeighbouringTDDCellMeasurementInformation,
				-- Applicable to 3.84Mcps TDD only
				...,
				extension-neighbouringCellMeasurementInformation	Extension-neighbouringCellMeasurementInformation
			}

Extension-neighbouringCellMeasurementInformation	::=	ProtocolIE-Single-Container {{ Extension-neighbouringCellMeasurementInformationIE }}

Extension-neighbouringCellMeasurementInformationIE NBAP-PROTOCOL-IES ::= {
	{ ID id-neighbouringTDDCellMeasurementInformationLCR	CRITICALITY reject	TYPE NeighbouringTDDCellMeasurementInformationLCR	PRESENCE mandatory },	-- Applicable to 1.28Mcps TDD only
	...
}

NeighbouringFDDCellMeasurementInformation ::= SEQUENCE {
	uC-Id								UC-Id,
	uARFCN								UARFCN,
	primaryScramblingCode				PrimaryScramblingCode,
	iE-Extensions						ProtocolExtensionContainer { { NeighbouringFDDCellMeasurementInformationItem-ExtIEs} } OPTIONAL,
	...
}

NeighbouringFDDCellMeasurementInformationItem-ExtIEs NBAP-PROTOCOL-EXTENSION ::= {
	...
}

NeighbouringTDDCellMeasurementInformation ::= SEQUENCE {
	uC-Id								UC-Id,
	uARFCN								UARFCN,
	cellParameterID						CellParameterID,
	timeSlot							TimeSlot						OPTIONAL,
	midambleShiftAndBurstType			MidambleShiftAndBurstType		OPTIONAL,
	iE-Extensions						ProtocolExtensionContainer { { NeighbouringTDDCellMeasurementInformationItem-ExtIEs} } OPTIONAL,
	...
}

NeighbouringTDDCellMeasurementInformationItem-ExtIEs NBAP-PROTOCOL-EXTENSION ::= {
	...
}

NeighbouringTDDCellMeasurementInformationLCR ::= SEQUENCE {
	uC-Id								UC-Id,
	uARFCN								UARFCN,
	cellParameterID						CellParameterID,
	timeSlotLCR							TimeSlotLCR				OPTIONAL,
	midambleShiftLCR					MidambleShiftLCR		OPTIONAL,
	iE-Extensions						ProtocolExtensionContainer { { NeighbouringTDDCellMeasurementInformationLCRItem-ExtIEs} } OPTIONAL,
	...
}

NeighbouringTDDCellMeasurementInformationLCRItem-ExtIEs NBAP-PROTOCOL-EXTENSION ::= {
	...
}

NodeB-CommunicationContextID ::= INTEGER (0..1048575)

NStartMessage ::= INTEGER (1..8)

NSubCyclesPerCyclePeriod ::= INTEGER (1..16,...)

-- ==========================================
--	O
-- ==========================================

-- ==========================================
--	P
-- ==========================================

PagingIndicatorLength ::= ENUMERATED {
	v2,
	v4,
	v8,
	...
}

PayloadCRC-PresenceIndicator ::= ENUMERATED {
	cRC-Included,
	cRC-NotIncluded,
	...
}

PCCPCH-Power ::= INTEGER (-150..400,...)
-- PCCPCH-power = power * 10
-- If power <= -15 PCCPCH shall be set to -150
-- If power >= 40 PCCPCH shall be set to 400
-- Unit dBm, Range -15dBm .. +40 dBm, Step +0.1dB

PCP-Length ::= ENUMERATED{
	v0,
	v8
}

PDSCH-CodeMapping ::= SEQUENCE {
	dl-ScramblingCode				DL-ScramblingCode,
	signallingMethod					CHOICE {
		code-Range						PDSCH-CodeMapping-PDSCH-CodeMappingInformationList,
		tFCI-Range						PDSCH-CodeMapping-DSCH-MappingInformationList,
		explicit							PDSCH-CodeMapping-PDSCH-CodeInformationList,
		...,
		replace							PDSCH-CodeMapping-ReplacedPDSCH-CodeInformationList
	},
	iE-Extensions							ProtocolExtensionContainer  { { PDSCH-CodeMapping-ExtIEs} }		OPTIONAL,
	...
}

PDSCH-CodeMapping-ExtIEs NBAP-PROTOCOL-EXTENSION ::= {
	...
}

PDSCH-CodeMapping-CodeNumberComp ::= INTEGER (0..maxCodeNrComp-1)

PDSCH-CodeMapping-SpreadingFactor ::= ENUMERATED {
	v4,
	v8,
	v16,
	v32,
	v64,
	v128,
	v256,
	...
}

PDSCH-CodeMapping-PDSCH-CodeMappingInformationList ::= SEQUENCE (SIZE (1..maxNrOfCodeGroups)) OF
	SEQUENCE {
		spreadingFactor				PDSCH-CodeMapping-SpreadingFactor,
		multi-CodeInfo				PDSCH-Multi-CodeInfo,
		start-CodeNumber				PDSCH-CodeMapping-CodeNumberComp,
		stop-CodeNumber				PDSCH-CodeMapping-CodeNumberComp,
		iE-Extensions					ProtocolExtensionContainer  { { PDSCH-CodeMapping-PDSCH-CodeMappingInformationList-ExtIEs} }		OPTIONAL,
		...
}

PDSCH-CodeMapping-PDSCH-CodeMappingInformationList-ExtIEs NBAP-PROTOCOL-EXTENSION ::= {
	...
}

PDSCH-CodeMapping-DSCH-MappingInformationList ::= SEQUENCE (SIZE (1..maxNrOfTFCIGroups)) OF
	SEQUENCE {
		maxTFCI-field2-Value			PDSCH-CodeMapping-MaxTFCI-Field2-Value,
		spreadingFactor				PDSCH-CodeMapping-SpreadingFactor,
		multi-CodeInfo				PDSCH-Multi-CodeInfo,
		codeNumber					PDSCH-CodeMapping-CodeNumberComp,
		iE-Extensions					ProtocolExtensionContainer  { { PDSCH-CodeMapping-DSCH-MappingInformationList-ExtIEs} }		OPTIONAL,
		...
}

PDSCH-CodeMapping-DSCH-MappingInformationList-ExtIEs NBAP-PROTOCOL-EXTENSION ::= {
	...
}

PDSCH-CodeMapping-MaxTFCI-Field2-Value ::= INTEGER (1..1023)

PDSCH-CodeMapping-PDSCH-CodeInformationList ::= SEQUENCE (SIZE (1..maxNrOfTFCI2Combs)) OF
	SEQUENCE {
		spreadingFactor				PDSCH-CodeMapping-SpreadingFactor,
		multi-CodeInfo				PDSCH-Multi-CodeInfo,
		codeNumber					PDSCH-CodeMapping-CodeNumberComp,
		iE-Extensions					ProtocolExtensionContainer  { { PDSCH-CodeMapping-PDSCH-CodeInformationList-ExtIEs} }		OPTIONAL,
		...
}

PDSCH-CodeMapping-PDSCH-CodeInformationList-ExtIEs NBAP-PROTOCOL-EXTENSION ::= {
	...
}

PDSCH-CodeMapping-ReplacedPDSCH-CodeInformationList ::= SEQUENCE (SIZE (1..maxNrOfTFCI2Combs)) OF
	SEQUENCE {
		tfci-Field2					TFCS-MaxTFCI-field2-Value,
		spreadingFactor				PDSCH-CodeMapping-SpreadingFactor,
		multi-CodeInfo				PDSCH-Multi-CodeInfo,
		codeNumber					PDSCH-CodeMapping-CodeNumberComp,
		iE-Extensions				ProtocolExtensionContainer { { PDSCH-CodeMapping-ReplacedPDSCH-CodeInformationList-ExtIEs} }		OPTIONAL,
	...
}

PDSCH-CodeMapping-ReplacedPDSCH-CodeInformationList-ExtIEs NBAP-PROTOCOL-EXTENSION ::= {
	...
}

PDSCH-Multi-CodeInfo ::= INTEGER (1..16)

PDSCH-ID ::= INTEGER (0..255)

PDSCHSet-ID ::= INTEGER (0..255)

PICH-Mode ::= ENUMERATED {
	v18,
	v36,
	v72,
	v144,
	...
}

PICH-Power ::= INTEGER (-10..5)
-- Unit dB, Range -10dB .. +5dB, Step +1dB

PowerAdjustmentType ::= ENUMERATED {
	none,
	common,
	individual
}

PowerOffset ::= INTEGER (0..24)
-- PowerOffset = offset * 0.25
-- Unit dB, Range 0dB .. +6dB, Step +0.25dB

PowerRaiseLimit ::= INTEGER (0..10)

PRACH-Midamble ::= ENUMERATED {
	inverted,
	direct,
	...
}

PRC ::= INTEGER (-2047..2047)
--pseudo range correction; scaling factor 0.32 meters

PRCDeviation ::= ENUMERATED {
   one,
   two,
   five,
   ten,
   ...
}

PreambleSignatures ::= BIT STRING {
									signature15(0),
									signature14(1),
									signature13(2),
									signature12(3),
									signature11(4),
									signature10(5),
									signature9(6),
									signature8(7),
									signature7(8),
									signature6(9),
									signature5(10),
									signature4(11),
									signature3(12),
									signature2(13),
									signature1(14),
									signature0(15)
									} (SIZE (16))

PreambleThreshold ::= INTEGER (0..72)
-- 0= -36.0dB, 1= -35.5dB, ... , 72= 0.0dB

PredictedSFNSFNDeviationLimit ::=INTEGER (1..256)
-- Unit chip, Step 1/16 chip, Range 1/16..16 chip

PredictedTUTRANGPSDeviationLimit ::= INTEGER (1..256)
-- Unit chip, Step 1/16 chip, Range 1/16..16 chip

Pre-emptionCapability ::= ENUMERATED {
	shall-not-trigger-pre-emption,
	may-trigger-pre-emption
}

Pre-emptionVulnerability ::= ENUMERATED {
	not-pre-emptable,
	pre-emptable
}

PrimaryCPICH-Power ::= INTEGER(-100..500)
-- step 0.1 (Range –10.0..50.0) Unit is dBm

PrimaryScramblingCode ::= INTEGER (0..511)

PriorityLevel				::= INTEGER (0..15)
-- 0 = spare, 1 = highest priority, ...14 = lowest priority and 15 = no priority

PriorityQueue-Id ::= INTEGER (0..maxNrOfPriorityQueues-1)

PriorityQueue-InfoList ::= SEQUENCE (SIZE (1..maxNrOfPriorityQueues)) OF PriorityQueue-InfoItem

PriorityQueue-InfoItem ::= SEQUENCE {
	priorityQueueId						PriorityQueue-Id,
	schedulingPriorityIndicator			SchedulingPriorityIndicator,
	mAC-hsWindowSize					MAC-hsWindowSize,
	macdPDU-Size-Index					MACdPDU-Size-Indexlist,
	iE-Extensions						ProtocolExtensionContainer { { PriorityQueue-InfoItem-ExtIEs} }		OPTIONAL,
	...
}

PriorityQueue-InfoItem-ExtIEs NBAP-PROTOCOL-EXTENSION ::= {
	...
}

PriorityQueue-InfoList-to-Modify ::= SEQUENCE (SIZE (1..maxNrOfPriorityQueues)) OF PriorityQueue-InfoItem-to-Modify

PriorityQueue-InfoItem-to-Modify ::= SEQUENCE {
	priorityQueueId						PriorityQueue-Id,
	schedulingPriorityIndicator			SchedulingPriorityIndicator									OPTIONAL,
	mAC-hsWindowSize					MAC-hsWindowSize											OPTIONAL,
	macdPDU-Size-Index-to-Modify		MACdPDU-Size-Indexlist-to-Modify							OPTIONAL,
	iE-Extensions						ProtocolExtensionContainer { { PriorityQueue-InfoItem-to-Modify-ExtIEs} }		OPTIONAL,
	...
}

PriorityQueue-InfoItem-to-Modify-ExtIEs NBAP-PROTOCOL-EXTENSION ::= {
	...
}

PrimaryCCPCH-RSCP ::= INTEGER (0..91)

PropagationDelay ::= INTEGER (0..255)
-- Unit: chips, step size 3 chips
-- example: 0 = 0chip, 1 = 3chips

SCH-TimeSlot ::= INTEGER (0..6)

PunctureLimit ::= INTEGER (0..15)
-- 0: 40%; 1: 44%; ... 14: 96%; 15: 100%

PUSCH-ID ::= INTEGER (0..255)

PUSCHSet-ID ::= INTEGER (0..255)

-- ==========================================
--	Q
-- ==========================================

QE-Selector ::= ENUMERATED {
	selected,
	non-selected
}

Qth-Parameter ::= INTEGER (-20..0)
-- Unit dB, Step 1dB

-- ==========================================
--	R
-- ==========================================

RACH-SlotFormat ::= ENUMERATED {
	v0,
	v1,
	v2,
	v3,
	...
}

RACH-SubChannelNumbers ::= BIT STRING {
										subCh11(0),
										subCh10(1),
									 	subCh9(2),
									 	subCh8(3),
									 	subCh7(4),
									 	subCh6(5),
									 	subCh5(6),
									 	subCh4(7),
									 	subCh3(8),
									 	subCh2(9),
									 	subCh1(10),
									 	subCh0(11)
										} (SIZE (12))

RL-Specific-DCH-Info ::= SEQUENCE (SIZE (1..maxNrOfDCHs)) OF RL-Specific-DCH-Info-Item

RL-Specific-DCH-Info-Item ::= SEQUENCE {
	dCH-id					DCH-ID,
	bindingID				BindingID															OPTIONAL,
	transportlayeraddress	TransportLayerAddress												OPTIONAL,
	iE-Extensions			ProtocolExtensionContainer { { RL-Specific-DCH-Info-Item-ExtIEs} }	OPTIONAL,
	...
}

RL-Specific-DCH-Info-Item-ExtIEs NBAP-PROTOCOL-EXTENSION ::= {
	...
}

Range-Correction-Rate ::= INTEGER (-127..127)
-- scaling factor 0.032 m/s

ReferenceClockAvailability ::= ENUMERATED {
	available,
	notAvailable
}

ReferenceSFNoffset ::= INTEGER (0..255)

RepetitionLength ::= INTEGER (1..63)

RepetitionPeriod ::= ENUMERATED {
	v1,
	v2,
	v4,
	v8,
	v16,
	v32,
	v64,
	...
}

RepetitionNumber0 ::= INTEGER (0..255)

RepetitionNumber1 ::= INTEGER (1..256)

RefTFCNumber ::= INTEGER (0..3)

ReportCharacteristics ::= CHOICE {
	onDemand				NULL,
	periodic				ReportCharacteristicsType-ReportPeriodicity,
	event-a				ReportCharacteristicsType-EventA,
	event-b				ReportCharacteristicsType-EventB,
	event-c				ReportCharacteristicsType-EventC,
	event-d				ReportCharacteristicsType-EventD,
	event-e				ReportCharacteristicsType-EventE,
	event-f				ReportCharacteristicsType-EventF,
	...,
	extension-ReportCharacteristics		Extension-ReportCharacteristics
}

Extension-ReportCharacteristics	::= ProtocolIE-Single-Container {{ Extension-ReportCharacteristicsIE }}

Extension-ReportCharacteristicsIE NBAP-PROTOCOL-IES ::= {
	{ ID id-ReportCharacteristicsType-OnModification	CRITICALITY reject	TYPE ReportCharacteristicsType-OnModification		PRESENCE mandatory }
}

ReportCharacteristicsType-EventA ::= SEQUENCE {
	measurementThreshold			ReportCharacteristicsType-MeasurementThreshold,
	measurementHysteresisTime		ReportCharacteristicsType-ScaledMeasurementHysteresisTime			OPTIONAL,
	iE-Extensions					ProtocolExtensionContainer { { ReportCharacteristicsType-EventA-ExtIEs} }		OPTIONAL,
	...
	}

ReportCharacteristicsType-EventA-ExtIEs NBAP-PROTOCOL-EXTENSION ::= {
	...
}

ReportCharacteristicsType-EventB ::= SEQUENCE {
	measurementThreshold			ReportCharacteristicsType-MeasurementThreshold,
	measurementHysteresisTime		ReportCharacteristicsType-ScaledMeasurementHysteresisTime			OPTIONAL,
	iE-Extensions					ProtocolExtensionContainer { { ReportCharacteristicsType-EventB-ExtIEs} }		OPTIONAL,
	...
	}

ReportCharacteristicsType-EventB-ExtIEs NBAP-PROTOCOL-EXTENSION ::= {
	...
}

ReportCharacteristicsType-EventC ::= SEQUENCE {
	measurementIncreaseThreshold	ReportCharacteristicsType-MeasurementIncreaseDecreaseThreshold,
	measurementChangeTime			ReportCharacteristicsType-ScaledMeasurementChangeTime,
	iE-Extensions					ProtocolExtensionContainer { { ReportCharacteristicsType-EventC-ExtIEs} }		OPTIONAL,
	...
	}

ReportCharacteristicsType-EventC-ExtIEs NBAP-PROTOCOL-EXTENSION ::= {
	...
}

ReportCharacteristicsType-EventD ::= SEQUENCE {
	measurementDecreaseThreshold	ReportCharacteristicsType-MeasurementIncreaseDecreaseThreshold,
	measurementChangeTime			ReportCharacteristicsType-ScaledMeasurementChangeTime,
	iE-Extensions					ProtocolExtensionContainer { { ReportCharacteristicsType-EventD-ExtIEs} }		OPTIONAL,
	...
	}

ReportCharacteristicsType-EventD-ExtIEs NBAP-PROTOCOL-EXTENSION ::= {
	...
}

ReportCharacteristicsType-EventE ::= SEQUENCE {
	measurementThreshold1			ReportCharacteristicsType-MeasurementThreshold,
	measurementThreshold2			ReportCharacteristicsType-MeasurementThreshold				OPTIONAL,
	measurementHysteresisTime		ReportCharacteristicsType-ScaledMeasurementHysteresisTime	OPTIONAL,
	reportPeriodicity				ReportCharacteristicsType-ReportPeriodicity					OPTIONAL,
	iE-Extensions					ProtocolExtensionContainer { { ReportCharacteristicsType-EventE-ExtIEs} }		OPTIONAL,
	...
	}

ReportCharacteristicsType-EventE-ExtIEs NBAP-PROTOCOL-EXTENSION ::= {
	...
}

ReportCharacteristicsType-EventF ::= SEQUENCE {
	measurementThreshold1			ReportCharacteristicsType-MeasurementThreshold,
	measurementThreshold2			ReportCharacteristicsType-MeasurementThreshold				OPTIONAL,
	measurementHysteresisTime		ReportCharacteristicsType-ScaledMeasurementHysteresisTime	OPTIONAL,
	reportPeriodicity				ReportCharacteristicsType-ReportPeriodicity					OPTIONAL,
	iE-Extensions					ProtocolExtensionContainer { { ReportCharacteristicsType-EventF-ExtIEs} }		OPTIONAL,
	...
	}

ReportCharacteristicsType-EventF-ExtIEs NBAP-PROTOCOL-EXTENSION ::= {
	...
}

ReportCharacteristicsType-OnModification ::= SEQUENCE {
	measurementThreshold			ReportCharacteristicsType-MeasurementThreshold,
	iE-Extensions					ProtocolExtensionContainer { { ReportCharacteristicsType-OnModification-ExtIEs} }		OPTIONAL,
		...
	}

ReportCharacteristicsType-OnModification-ExtIEs NBAP-PROTOCOL-EXTENSION ::= {
	...
}

ReportCharacteristicsType-MeasurementIncreaseDecreaseThreshold ::= CHOICE {
	received-total-wide-band-power							Received-total-wide-band-power-Value-IncrDecrThres,
	transmitted-carrier-power		Transmitted-Carrier-Power-Value,
	acknowledged-prach-preambles			Acknowledged-PRACH-preambles-Value,
	uL-TimeslotISCP					UL-TimeslotISCP-Value-IncrDecrThres,
	sir							SIR-Value-IncrDecrThres,
	sir-error					SIR-Error-Value-IncrDecrThres,
	transmitted-code-power			Transmitted-Code-Power-Value-IncrDecrThres,
	rscp							RSCP-Value-IncrDecrThres,
	round-trip-time					Round-Trip-Time-IncrDecrThres,
	acknowledged-PCPCH-access-preambles		Acknowledged-PCPCH-access-preambles,
	detected-PCPCH-access-preambles			Detected-PCPCH-access-preambles,
	...
}

ReportCharacteristicsType-MeasurementThreshold ::= CHOICE {
	received-total-wide-band-power							Received-total-wide-band-power-Value,
	transmitted-carrier-power		Transmitted-Carrier-Power-Value,
	acknowledged-prach-preambles			Acknowledged-PRACH-preambles-Value,
	uL-TimeslotISCP					UL-TimeslotISCP-Value,
	sir							SIR-Value,
	sir-error					SIR-Error-Value,
	transmitted-code-power			Transmitted-Code-Power-Value,
	rscp							RSCP-Value,
	rx-timing-deviation				Rx-Timing-Deviation-Value,
	round-trip-time					Round-Trip-Time-Value,
	acknowledged-PCPCH-access-preambles		Acknowledged-PCPCH-access-preambles,
	detected-PCPCH-access-preambles			Detected-PCPCH-access-preambles,
	...,
	extension-ReportCharacteristicsType-MeasurementThreshold		Extension-ReportCharacteristicsType-MeasurementThreshold
}

Extension-ReportCharacteristicsType-MeasurementThreshold	::= ProtocolIE-Single-Container {{ Extension-ReportCharacteristicsType-MeasurementThresholdIE }}

Extension-ReportCharacteristicsType-MeasurementThresholdIE NBAP-PROTOCOL-IES ::= {
	{ ID id-TUTRANGPSMeasurementThresholdInformation	CRITICALITY reject	TYPE TUTRANGPSMeasurementThresholdInformation		PRESENCE mandatory }|
	{ ID id-SFNSFNMeasurementThresholdInformation	CRITICALITY reject	TYPE SFNSFNMeasurementThresholdInformation		PRESENCE mandatory }|
	{ ID id-Rx-Timing-Deviation-Value-LCR	CRITICALITY reject	TYPE Rx-Timing-Deviation-Value-LCR	PRESENCE mandatory}
}

ReportCharacteristicsType-ScaledMeasurementChangeTime ::= CHOICE {
	msec				MeasurementChangeTime-Scaledmsec,
	...
}

MeasurementChangeTime-Scaledmsec ::= INTEGER (1..6000,...)
-- MeasurementChangeTime-Scaledmsec = Time * 10
-- Unit ms, Range 10ms .. 60000ms(1min), Step 10ms

ReportCharacteristicsType-ScaledMeasurementHysteresisTime ::= CHOICE {
	msec				MeasurementHysteresisTime-Scaledmsec,
	...
}

MeasurementHysteresisTime-Scaledmsec ::= INTEGER (1..6000,...)
-- MeasurementHysteresisTime-Scaledmsec = Time * 10
-- Unit ms, Range 10ms .. 60000ms(1min), Step 10ms

ReportCharacteristicsType-ReportPeriodicity ::= CHOICE {
	msec 				ReportPeriodicity-Scaledmsec,
	min					ReportPeriodicity-Scaledmin,
	...
}

ReportPeriodicity-Scaledmsec ::= INTEGER (1..6000,...)
-- ReportPeriodicity-msec = ReportPeriodicity * 10
-- Unit ms, Range 10ms .. 60000ms(1min), Step 10ms

ReportPeriodicity-Scaledmin ::= INTEGER (1..60,...)
-- Unit min, Range 1min .. 60min(hour), Step 1min

ReportPeriodicity-Scaledhour ::= INTEGER (1..24,...)
-- Unit hour, Range 1hour .. 24hours(day), Step 1hour

ResourceOperationalState ::= ENUMERATED {
	enabled,
	disabled
}

RL-ID ::= INTEGER (0..31)

RL-Set-ID				::= INTEGER (0..31)

Round-Trip-Time-IncrDecrThres ::= INTEGER(0..32766)

RNC-ID					::= INTEGER (0..4095)

Round-Trip-Time-Value ::= INTEGER(0..32767)
-- According to mapping in [22]

RSCP-Value ::= INTEGER (0..127)
-- According to mapping in [23]

RSCP-Value-IncrDecrThres ::= INTEGER (0..126)

Received-total-wide-band-power-Value ::= INTEGER(0..621)
-- According to mapping in [22]/[23]

Received-total-wide-band-power-Value-IncrDecrThres ::= INTEGER (0..620)

RequestedDataValueInformation ::= CHOICE {
	informationAvailable		InformationAvailable,
	informationnotAvailable		InformationnotAvailable
}

InformationAvailable::= SEQUENCE {
	requesteddataValue		RequestedDataValue,
	ie-Extensions			ProtocolExtensionContainer { { InformationAvailableItem-ExtIEs} }		OPTIONAL,
	...
}

InformationAvailableItem-ExtIEs NBAP-PROTOCOL-EXTENSION ::= {
	...
}

InformationnotAvailable ::= NULL

RequestedDataValue ::= SEQUENCE {
	dgps-corrections     DGPSCorrections  OPTIONAL,
    gps-navandrecovery   GPS-NavigationModel-and-TimeRecovery   OPTIONAL,
    gps-ionos-model      GPS-Ionospheric-Model  OPTIONAL,
    gps-utc-model        GPS-UTC-Model         	OPTIONAL,
    gps-almanac          GPS-Almanac            OPTIONAL,
    gps-rt-integrity     GPS-RealTime-Integrity  OPTIONAL,
    gpsrxpos             GPS-RX-POS              OPTIONAL,
	...
}

Rx-Timing-Deviation-Value ::= INTEGER (0..8191)
-- According to mapping in [23]

Rx-Timing-Deviation-Value-LCR ::= INTEGER (0..511)
-- According to mapping in [23]

-- ==========================================
--	S
-- ==========================================

AdjustmentPeriod			::= INTEGER(1..256)
-- Unit Frame

SAT-ID ::= INTEGER (0..63) 

SAT-Info-Almanac ::= SEQUENCE (SIZE (1..maxNoSat)) OF SAT-Info-Almanac-Item

SAT-Info-Almanac-Item ::= SEQUENCE {
	data-id			   DATA-ID,
    sat-id             SAT-ID,
    gps-e-alm          BIT STRING (SIZE (16)),
    gps-toa-alm        BIT STRING (SIZE (8)),     
    gps-delta-I-alm    BIT STRING (SIZE (16)),
    omegadot-alm       BIT STRING (SIZE (16)),
    svhealth-alm       BIT STRING (SIZE (8)),
    gps-a-sqrt-alm     BIT STRING (SIZE (24)),
    omegazero-alm      BIT STRING (SIZE (24)),
    m-zero-alm         BIT STRING (SIZE (24)),
    gps-omega-alm      BIT STRING (SIZE (24)),
    gps-af-zero-alm    BIT STRING (SIZE (11)),
    gps-af-one-alm     BIT STRING (SIZE (11)),
    ie-Extensions	   ProtocolExtensionContainer { { SAT-Info-Almanac-Item-ExtIEs} }		OPTIONAL,
   ...
}

SAT-Info-Almanac-Item-ExtIEs NBAP-PROTOCOL-EXTENSION ::= {
	...
} 

SAT-Info-DGPSCorrections ::= SEQUENCE (SIZE (1..maxNoSat)) OF SAT-Info-DGPSCorrections-Item

SAT-Info-DGPSCorrections-Item ::= SEQUENCE {
    sat-id                                	SAT-ID,
    iode-dgps                           	BIT STRING (SIZE (8)),
    udre            						UDRE,
    prc             						PRC,
    range-correction-rate             		Range-Correction-Rate,
    ie-Extensions							ProtocolExtensionContainer { { SAT-Info-DGPSCorrections-Item-ExtIEs} }  OPTIONAL,
   ...
}

SAT-Info-DGPSCorrections-Item-ExtIEs NBAP-PROTOCOL-EXTENSION ::= {
	...
}

SATInfo-RealTime-Integrity ::= SEQUENCE (SIZE (1..maxNoSat)) OF SAT-Info-RealTime-Integrity-Item

SAT-Info-RealTime-Integrity-Item ::= SEQUENCE {
  bad-sat-id       SAT-ID,
  ie-Extensions	   ProtocolExtensionContainer { { SAT-Info-RealTime-Integrity-Item-ExtIEs} }		OPTIONAL,
   ...
}

SAT-Info-RealTime-Integrity-Item-ExtIEs NBAP-PROTOCOL-EXTENSION ::= {
	...
}

ScaledAdjustmentRatio			::= INTEGER(0..100)
-- AdjustmentRatio  = ScaledAdjustmentRatio / 100

MaxAdjustmentStep			::= INTEGER(1..10)
-- Unit Slot

SchedulingPriorityIndicator 			::= INTEGER (0..15)		 -- lowest (0), highest (15)

SID ::= INTEGER (0..maxNrOfMACdPDUIndexes-1)

ScramblingCodeNumber ::= INTEGER (0..15)

SecondaryCCPCH-SlotFormat ::= INTEGER(0..17,...)

Segment-Type ::= ENUMERATED {
		first-segment, 
		first-segment-short,
		subsequent-segment,
		last-segment, 
		last-segment-short, 
		complete-SIB, 
		complete-SIB-short,
		...
}

S-FieldLength ::= ENUMERATED {
		v1,
		v2,
		...
}

SFN ::= INTEGER (0..4095)

SFNSFN-FDD ::= INTEGER (0..614399)

SFNSFN-TDD ::= INTEGER (0..40961) 

SFNSFNChangeLimit ::= INTEGER (1..256)
-- Unit chip, Step 1/16 chip, Range 1/16..16 chip

SFNSFNDriftRate ::= INTEGER (-100..100)
-- Unit chip/s, Step 1/256 chip/s, Range -100/256..+100/256 chip/s

SFNSFNDriftRateQuality ::= INTEGER (0..100)
-- Unit chip/s, Step 1/256 chip/s, Range 0..100/256 chip/s

SFNSFNMeasurementThresholdInformation::= SEQUENCE {
	sFNSFNChangeLimit					SFNSFNChangeLimit					OPTIONAL,
	predictedSFNSFNDeviationLimit		PredictedSFNSFNDeviationLimit		OPTIONAL,
	iE-Extensions					ProtocolExtensionContainer { { SFNSFNMeasurementThresholdInformation-ExtIEs} }		OPTIONAL,
	...
}

SFNSFNMeasurementThresholdInformation-ExtIEs NBAP-PROTOCOL-EXTENSION ::= {
	...
}

SFNSFNMeasurementValueInformation ::= SEQUENCE {
	successfullNeighbouringCellSFNSFNObservedTimeDifferenceMeasurementInformation		SEQUENCE (SIZE(1..maxNrOfMeasNCell)) OF
		SEQUENCE {
			uC-Id						UC-Id,
			sFNSFNValue		SFNSFNValue,
			sFNSFNQuality		SFNSFNQuality						OPTIONAL,
			sFNSFNDriftRate		SFNSFNDriftRate,
			sFNSFNDriftRateQuality		SFNSFNDriftRateQuality		OPTIONAL,
			sFNSFNTimeStampInformation				SFNSFNTimeStampInformation,
			iE-Extensions		ProtocolExtensionContainer { { SuccessfullNeighbouringCellSFNSFNObservedTimeDifferenceMeasurementInformationItem-ExtIEs} }		OPTIONAL,
			...
		},
	unsuccessfullNeighbouringCellSFNSFNObservedTimeDifferenceMeasurementInformation		SEQUENCE (SIZE(0..maxNrOfMeasNCell-1)) OF
		SEQUENCE {
			uC-Id						UC-Id,
			iE-Extensions		ProtocolExtensionContainer { { UnsuccessfullNeighbouringCellSFNSFNObservedTimeDifferenceMeasurementInformationItem-ExtIEs} }		OPTIONAL,
				...
		},
	iE-Extensions		ProtocolExtensionContainer { { SFNSFNMeasurementValueInformationItem-ExtIEs} }		OPTIONAL,
	...
}

SFNSFNMeasurementValueInformationItem-ExtIEs NBAP-PROTOCOL-EXTENSION ::= {
	...
}

SuccessfullNeighbouringCellSFNSFNObservedTimeDifferenceMeasurementInformationItem-ExtIEs NBAP-PROTOCOL-EXTENSION ::= {
	...
}

UnsuccessfullNeighbouringCellSFNSFNObservedTimeDifferenceMeasurementInformationItem-ExtIEs NBAP-PROTOCOL-EXTENSION ::= {
	...
}

SFNSFNQuality ::= INTEGER (0..255)
-- Unit chip, Step 1/16 chip, Range 0.. 255/16 chip

ShutdownTimer ::= INTEGER (1..3600)
-- Unit sec

SIB-Originator ::= ENUMERATED {
	nodeB, 
	cRNC,
	...
}

SIR-Error-Value ::= INTEGER (0..125)
-- According to mapping in [22]

SFNSFNTimeStampInformation ::= CHOICE {
	sFNSFNTimeStamp-FDD		SFN,
	sFNSFNTimeStamp-TDD		SFNSFNTimeStamp-TDD,
	...}

SFNSFNTimeStamp-TDD::= SEQUENCE {
	sFN					SFN,
	timeSlot			TimeSlot,
	iE-Extensions					ProtocolExtensionContainer { { SFNSFNTimeStamp-ExtIEs} }		OPTIONAL,
	...
}

SFNSFNTimeStamp-ExtIEs NBAP-PROTOCOL-EXTENSION ::= {
	...
}

SFNSFNValue ::= CHOICE {
	sFNSFN-FDD		SFNSFN-FDD,
	sFNSFN-TDD		SFNSFN-TDD,
	...
}

SIR-Error-Value-IncrDecrThres ::= INTEGER (0..124)

SIR-Value ::= INTEGER (0..63)
-- According to mapping in [22]/[23]

SIR-Value-IncrDecrThres ::= INTEGER (0..62)

SignallingBearerRequestIndicator::= ENUMERATED {bearerRequested}

SpecialBurstScheduling ::= INTEGER (1..256)

SSDT-Cell-Identity ::= ENUMERATED {a, b, c, d, e, f, g, h}

SSDT-CellID-Length ::= ENUMERATED {
	short,
	medium,
	long
}

SSDT-Indication ::= ENUMERATED {
	ssdt-active-in-the-UE,
	ssdt-not-active-in-the-UE
}

Start-Of-Audit-Sequence-Indicator ::= ENUMERATED {
	start-of-audit-sequence,
	not-start-of-audit-sequence
}

STTD-Indicator ::= ENUMERATED {
	active,
	inactive,
	...
}

SSDT-SupportIndicator ::= ENUMERATED {
	sSDT-Supported,
	sSDT-not-supported
}

SyncCase ::= INTEGER (1..2,...)

SYNCDlCodeId ::= INTEGER (1..32,...)

SyncFrameNumber ::= INTEGER (1..10)

SynchronisationReportCharacteristics ::= SEQUENCE {
	synchronisationReportCharacteristicsType	SynchronisationReportCharacteristicsType,
	synchronisationReportCharactThreExc			SynchronisationReportCharactThreExc		OPTIONAL,
		-- Thie IE shall be included if the synchronisationReportCharacteristicsType IE is set to “thresholdExceeding”.
	iE-Extensions								ProtocolExtensionContainer { { SynchronisationReportCharacteristics-ExtIEs } }	OPTIONAL,
	...
}

SynchronisationReportCharacteristics-ExtIEs	NBAP-PROTOCOL-EXTENSION ::= {
	{ ID id-SyncDLCodeIdThreInfoLCR	CRITICALITY	ignore EXTENSION	SyncDLCodeIdThreInfoLCR		PRESENCE optional },
	...
}

SynchronisationReportCharactThreExc ::= 	SEQUENCE (SIZE (1..maxNrOfCellSyncBursts)) OF SynchronisationReportCharactThreInfoItem  -- Mandatory for 3.84Mcps TDD only

SynchronisationReportCharactThreInfoItem ::= SEQUENCE {
	syncFrameNumber				SyncFrameNumber,
	cellSyncBurstInformation	SEQUENCE (SIZE (1.. maxNrOfReceptsPerSyncFrame)) OF SynchronisationReportCharactCellSyncBurstInfoItem,
	iE-Extensions				ProtocolExtensionContainer { { SynchronisationReportCharactThreInfoItem-ExtIEs } }		OPTIONAL,
	...
}

SynchronisationReportCharactThreInfoItem-ExtIEs NBAP-PROTOCOL-EXTENSION ::= {
	...
}

SynchronisationReportCharactCellSyncBurstInfoItem ::= SEQUENCE {
	cellSyncBurstCode 				CellSyncBurstCode,
	cellSyncBurstCodeShift 			CellSyncBurstCodeShift,
	cellSyncBurstTiming 			CellSyncBurstTiming				OPTIONAL,
	cellSyncBurstTimingThreshold 	CellSyncBurstTimingThreshold	OPTIONAL,
	iE-Extensions					ProtocolExtensionContainer { { SynchronisationReportCharactCellSyncBurstInfoItem-ExtIEs } }		OPTIONAL,
	...
}

SynchronisationReportCharactCellSyncBurstInfoItem-ExtIEs NBAP-PROTOCOL-EXTENSION ::= {
	...
}

SyncDLCodeIdThreInfoLCR ::= SEQUENCE (SIZE (0..maxNrOfSyncFramesLCR)) OF SyncDLCodeIdThreInfoList  --Mandatory for 1.28Mcps TDD only

SyncDLCodeIdThreInfoList ::= SEQUENCE {
	syncFrameNoToReceive			SyncFrameNumber,
	syncDLCodeIdInfoLCR				SyncDLCodeInfoListLCR,
	iE-Extensions					ProtocolExtensionContainer { { SyncDLCodeIdThreInfoList-ExtIEs } }		OPTIONAL,
	...
}

SyncDLCodeIdThreInfoList-ExtIEs NBAP-PROTOCOL-EXTENSION ::= {
	...
}

SyncDLCodeInfoListLCR ::= SEQUENCE (SIZE (1..maxNrOfSyncDLCodesLCR)) OF SyncDLCodeInfoItemLCR

SyncDLCodeInfoItemLCR ::= SEQUENCE {
	syncDLCodeId					SYNCDlCodeId,
	syncDLCodeIdArrivTime			CellSyncBurstTiming				OPTIONAL,
	syncDLCodeIdTimingThre			CellSyncBurstTimingThreshold	OPTIONAL,
	iE-Extensions					ProtocolExtensionContainer { { SyncDLCodeInfoItem-LCR-ExtIEs } }		OPTIONAL,
	...
}

SyncDLCodeInfoItem-LCR-ExtIEs NBAP-PROTOCOL-EXTENSION ::= {
	...
}

SynchronisationReportCharacteristicsType ::= ENUMERATED {
	frameRelated,
	sFNperiodRelated,
	cycleLengthRelated,
	thresholdExceeding,
	frequencyAcquisitionCompleted,
	...
}

SynchronisationReportType ::= ENUMERATED {
	initialPhase,
	steadyStatePhase,
	lateEntrantCell,
	frequencyAcquisition,
	...
}

-- ==========================================
--	T
-- ==========================================

T-Cell ::= ENUMERATED {
	v0,
	v1,
	v2,
	v3,
	v4,
	v5,
	v6,
	v7,
	v8,
	v9
}

T-RLFAILURE ::= INTEGER (0..255)
-- Unit seconds, Range 0s .. 25.5s, Step 0.1s

TDD-ChannelisationCode ::= ENUMERATED {
	chCode1div1,
	chCode2div1,
	chCode2div2,
	chCode4div1,
	chCode4div2,
	chCode4div3,
	chCode4div4,
	chCode8div1,
	chCode8div2,
	chCode8div3,
	chCode8div4,
	chCode8div5,
	chCode8div6,
	chCode8div7,
	chCode8div8,
	chCode16div1,
	chCode16div2,
	chCode16div3,
	chCode16div4,
	chCode16div5,
	chCode16div6,
	chCode16div7,
	chCode16div8,
	chCode16div9,
	chCode16div10,
	chCode16div11,
	chCode16div12,
	chCode16div13,
	chCode16div14,
	chCode16div15,
	chCode16div16,
	...
}

TDD-ChannelisationCodeLCR ::= SEQUENCE {
	tDD-ChannelisationCode			TDD-ChannelisationCode,
	modulation						Modulation, -- Modulation options for 1.28Mcps TDD in contrast to 3.84Mcps TDD
	iE-Extensions							ProtocolExtensionContainer { { TDD-ChannelisationCodeLCR-ExtIEs} }		OPTIONAL,
	...
}

TDD-ChannelisationCodeLCR-ExtIEs NBAP-PROTOCOL-EXTENSION ::= {
	...
}

TDD-DL-Code-Information ::= SEQUENCE (SIZE (1..maxNrOfDPCHs)) OF TDD-DL-Code-InformationItem

TDD-DL-Code-InformationItem	 ::= SEQUENCE {
	dPCH-ID									DPCH-ID,
	tdd-ChannelisationCode					TDD-ChannelisationCode,
	iE-Extensions							ProtocolExtensionContainer { { TDD-DL-Code-InformationItem-ExtIEs} }		OPTIONAL,
	...
}

TDD-DL-Code-InformationItem-ExtIEs NBAP-PROTOCOL-EXTENSION ::= {
	...
}

TDD-DL-Code-LCR-Information ::= SEQUENCE (SIZE (1..maxNrOfDPCHLCRs)) OF TDD-DL-Code-LCR-InformationItem

TDD-DL-Code-LCR-InformationItem ::= SEQUENCE {
	dPCH-ID									DPCH-ID,
	tdd-ChannelisationCodeLCR				TDD-ChannelisationCodeLCR,
	tdd-DL-DPCH-TimeSlotFormat-LCR			TDD-DL-DPCH-TimeSlotFormat-LCR,
	iE-Extensions							ProtocolExtensionContainer { { TDD-DL-Code-LCR-InformationItem-ExtIEs} }		OPTIONAL,
	...
}

TDD-DL-Code-LCR-InformationItem-ExtIEs NBAP-PROTOCOL-EXTENSION ::= {
	...
}

TDD-DL-DPCH-TimeSlotFormat-LCR ::= CHOICE {
	qPSK						QPSK-DL-DPCH-TimeSlotFormatTDD-LCR,
	eightPSK					EightPSK-DL-DPCH-TimeSlotFormatTDD-LCR,
	...
}

QPSK-DL-DPCH-TimeSlotFormatTDD-LCR ::= INTEGER(0..24,...)

EightPSK-DL-DPCH-TimeSlotFormatTDD-LCR ::= INTEGER(0..24,...)

TDD-DPCHOffset ::= CHOICE {
	initialOffset		INTEGER (0..255),
	noinitialOffset		INTEGER (0..63)
}

TDD-PhysicalChannelOffset ::= INTEGER (0..63)

TDD-TPC-DownlinkStepSize ::= ENUMERATED {
	step-size1,
	step-size2,
	step-size3,
	...
}

TransportFormatCombination-Beta ::= CHOICE {
	signalledGainFactors		SEQUENCE {
		gainFactor					CHOICE {
			fdd							SEQUENCE {
				betaC						BetaCD,
				betaD						BetaCD,
				iE-Extensions		ProtocolExtensionContainer { { GainFactorFDD-ExtIEs } }		OPTIONAL,
				...
			},
			tdd							BetaCD,
			...
		},
	    refTFCNumber				RefTFCNumber	OPTIONAL,
		iE-Extensions			ProtocolExtensionContainer { { SignalledGainFactors-ExtIEs } }		OPTIONAL,
		...
	},
	computedGainFactors				RefTFCNumber,
	...
}

GainFactorFDD-ExtIEs NBAP-PROTOCOL-EXTENSION ::= {
	...
}

SignalledGainFactors-ExtIEs NBAP-PROTOCOL-EXTENSION ::= {
	...
}

TDD-UL-Code-Information ::= SEQUENCE (SIZE (1..maxNrOfDPCHs)) OF TDD-UL-Code-InformationItem

TDD-UL-Code-InformationItem ::= SEQUENCE {
	dPCH-ID									DPCH-ID,
	tdd-ChannelisationCode					TDD-ChannelisationCode,
	iE-Extensions							ProtocolExtensionContainer { { TDD-UL-Code-InformationItem-ExtIEs} }		OPTIONAL,
	...
}

TDD-UL-Code-InformationItem-ExtIEs NBAP-PROTOCOL-EXTENSION ::= {
	...
}

TDD-UL-Code-LCR-Information ::= SEQUENCE (SIZE (1..maxNrOfDPCHLCRs)) OF TDD-UL-Code-LCR-InformationItem

TDD-UL-Code-LCR-InformationItem ::= SEQUENCE {
	dPCH-ID									DPCH-ID,
	tdd-ChannelisationCodeLCR				TDD-ChannelisationCodeLCR,
	tdd-UL-DPCH-TimeSlotFormat-LCR			TDD-UL-DPCH-TimeSlotFormat-LCR,
	iE-Extensions							ProtocolExtensionContainer { { TDD-UL-Code-LCR-InformationItem-ExtIEs} }		OPTIONAL,
	...
}

TDD-UL-Code-LCR-InformationItem-ExtIEs NBAP-PROTOCOL-EXTENSION ::= {
	...
}

TDD-UL-DPCH-TimeSlotFormat-LCR ::= CHOICE {
	qPSK						QPSK-UL-DPCH-TimeSlotFormatTDD-LCR,
	eightPSK					EightPSK-UL-DPCH-TimeSlotFormatTDD-LCR,
	...
}

QPSK-UL-DPCH-TimeSlotFormatTDD-LCR ::= INTEGER(0..69,...)

EightPSK-UL-DPCH-TimeSlotFormatTDD-LCR ::= INTEGER(0..24,...)

TFCI-Coding ::= ENUMERATED {
	v4,
	v8,
	v16,
	v32,
	...
}

TFCI-Presence ::= ENUMERATED {
	present,
	not-present
}

TFCI-SignallingMode ::= SEQUENCE {
	tFCI-SignallingOption		TFCI-SignallingMode-TFCI-SignallingOption,
	splitType				TFCI-SignallingMode-SplitType				OPTIONAL,
	-- This IE shall be present if the TFCI signalling option is split --
	lengthOfTFCI2				TFCI-SignallingMode-LengthOfTFCI2			OPTIONAL,
	iE-Extensions				ProtocolExtensionContainer { { TFCI-SignallingMode-ExtIEs} }		OPTIONAL,
	...
}

TFCI-SignallingMode-ExtIEs NBAP-PROTOCOL-EXTENSION ::= {
	...
}

TFCI-SignallingMode-LengthOfTFCI2 ::= INTEGER (1..10)

TFCI-SignallingMode-SplitType ::= ENUMERATED {
	hard, 
	logical
}

TFCI-SignallingMode-TFCI-SignallingOption ::= ENUMERATED {
	normal,
	split
}

TFCI2-BearerInformationResponse ::= SEQUENCE {
	bindingID										BindingID,
	transportLayerAddress							TransportLayerAddress,
	iE-Extensions									ProtocolExtensionContainer { { TFCI2-BearerInformationResponse-ExtIEs} }		OPTIONAL,
	...
}

TFCI2-BearerInformationResponse-ExtIEs NBAP-PROTOCOL-EXTENSION ::= {
	...
}

TFCI2BearerRequestIndicator ::= ENUMERATED {newBearerRequested}

TGD					::= INTEGER (0|15..269)
-- 0 = Undefined, only one transmission gap in the transmission gap pattern sequence 

TGPRC 				::= INTEGER (0..511)
-- 0 = infinity

TGPSID				::= INTEGER (1.. maxTGPS)

TGSN				::= INTEGER (0..14)

TimeSlot ::= INTEGER (0..14)

TimeSlotDirection ::= ENUMERATED {
	ul,
	dl,
	...
}

TimeSlotLCR ::= INTEGER (0..6)

TimeSlotStatus ::= ENUMERATED {
	active,
	not-active,
	...
}

TimingAdjustmentValue ::= CHOICE {
	initialPhase		INTEGER (0..255),
	steadyStatePhase	INTEGER (0..1048575)
}

TimingAdvanceApplied ::= ENUMERATED {
	yes,
	no
}
-- For 1.28Mcps TDD TimingAdvanceApplied = No

ToAWE ::= INTEGER (0..2559)
-- Unit ms

ToAWS ::= INTEGER (0..1279)
-- Unit ms

Transmission-Gap-Pattern-Sequence-Information ::= SEQUENCE (SIZE (1..maxTGPS)) OF
	SEQUENCE {
		tGPSID			TGPSID,
		tGSN			TGSN,
		tGL1			GapLength,
		tGL2			GapLength	OPTIONAL,
		tGD				TGD,
		tGPL1			GapDuration,
		tGPL2			GapDuration	OPTIONAL,
		uL-DL-mode		UL-DL-mode,
		downlink-Compressed-Mode-Method		Downlink-Compressed-Mode-Method		OPTIONAL,
			-- This IE shall be present if the UL/DL mode IE is set to "DL only" or "UL/DL"
		uplink-Compressed-Mode-Method		Uplink-Compressed-Mode-Method		OPTIONAL,
			-- This IE shall be present if the UL/DL mode IE is set to "UL only" or "UL/DL"
		dL-FrameType		DL-FrameType,
		delta-SIR1			DeltaSIR,
		delta-SIR-after1	DeltaSIR,
		delta-SIR2			DeltaSIR	OPTIONAL,
		delta-SIR-after2	DeltaSIR	OPTIONAL,
		iE-Extensions			ProtocolExtensionContainer { {Transmission-Gap-Pattern-Sequence-Information-ExtIEs} } OPTIONAL,
		...
	}

Transmission-Gap-Pattern-Sequence-Information-ExtIEs NBAP-PROTOCOL-EXTENSION ::= {
	...
}

TransmissionGapPatternSequenceCodeInformation	::= ENUMERATED{
code-change,
nocode-change
}

Transmitted-Carrier-Power-Value ::= INTEGER(0..100)
-- According to mapping in [22]/[23]

Transmitted-Code-Power-Value ::= INTEGER (0..127)
-- According to mapping in [22]/[23]

Transmitted-Code-Power-Value-IncrDecrThres ::= INTEGER (0..112,...)

TransmissionDiversityApplied ::= BOOLEAN
-- true: applied, false: not applied

TransmitDiversityIndicator ::= ENUMERATED {
	active,
	inactive
}

TFCS ::= SEQUENCE {
	tFCSvalues					CHOICE {
		no-Split-in-TFCI			TFCS-TFCSList,
		split-in-TFCI				SEQUENCE {
			transportFormatCombination-DCH		TFCS-DCHList,
			signallingMethod					CHOICE {
				tFCI-Range						TFCS-MapingOnDSCHList,
				explicit							TFCS-DSCHList,
				...
			},
			iE-Extensions						ProtocolExtensionContainer { { Split-in-TFCI-ExtIEs } }		OPTIONAL,	
			...
		},
	...
	},
	iE-Extensions		ProtocolExtensionContainer  { { TFCS-ExtIEs} }		OPTIONAL,
	...
}

Split-in-TFCI-ExtIEs NBAP-PROTOCOL-EXTENSION ::= {
	...
}

TFCS-ExtIEs NBAP-PROTOCOL-EXTENSION ::= {
	...
}

TFCS-TFCSList ::= SEQUENCE (SIZE (1..maxNrOfTFCs)) OF
	SEQUENCE {
		cTFC				TFCS-CTFC,
		tFC-Beta		TransportFormatCombination-Beta 	OPTIONAL,
		-- The IE shall be present if the TFCS concerns a UL DPCH or PRACH channel [FDD – or PCPCH channel].
		iE-Extensions		ProtocolExtensionContainer  { { TFCS-TFCSList-ExtIEs} }		OPTIONAL,
		...
}

TFCS-TFCSList-ExtIEs NBAP-PROTOCOL-EXTENSION ::= {
	...
}

TFCS-CTFC ::= CHOICE {
	ctfc2bit							INTEGER (0..3),
	ctfc4bit							INTEGER (0..15),
	ctfc6bit							INTEGER (0..63),
	ctfc8bit							INTEGER (0..255),
	ctfc12bit							INTEGER (0..4095),
	ctfc16bit							INTEGER (0..65535),
	ctfcmaxbit							INTEGER (0..maxCTFC)
}

TFCS-DCHList ::= SEQUENCE (SIZE (1..maxNrOfTFCI1Combs)) OF
	SEQUENCE {
		cTFC				TFCS-CTFC,
		iE-Extensions		ProtocolExtensionContainer  { { TFCS-DCHList-ExtIEs} }		OPTIONAL,
		...
}

TFCS-DCHList-ExtIEs NBAP-PROTOCOL-EXTENSION ::= {
	...
}

TFCS-MapingOnDSCHList ::= SEQUENCE (SIZE (1..maxNrOfTFCIGroups)) OF
	SEQUENCE {
		maxTFCI-field2-Value		TFCS-MaxTFCI-field2-Value,
		cTFC-DSCH				TFCS-CTFC,
		iE-Extensions				ProtocolExtensionContainer  { { TFCS-MapingOnDSCHList-ExtIEs} }		OPTIONAL,
	...
}

TFCS-MapingOnDSCHList-ExtIEs NBAP-PROTOCOL-EXTENSION ::= {
	...
}

TFCS-MaxTFCI-field2-Value ::= INTEGER (1..maxNrOfTFCI2Combs-1)

TFCS-DSCHList ::= SEQUENCE (SIZE (1..maxNrOfTFCI2Combs)) OF
	SEQUENCE {
		cTFC-DSCH				TFCS-CTFC,
		iE-Extensions				ProtocolExtensionContainer  { { TFCS-DSCHList-ExtIEs} }		OPTIONAL,
		...
}

TFCS-DSCHList-ExtIEs NBAP-PROTOCOL-EXTENSION ::= {
	...
}

TransportBearerRequestIndicator ::= ENUMERATED {
	bearerRequested,
	bearerNotRequested,
	...
}

TransportFormatSet ::= SEQUENCE {
	dynamicParts			TransportFormatSet-DynamicPartList,
	semi-staticPart			TransportFormatSet-Semi-staticPart,
	iE-Extensions			ProtocolExtensionContainer  { { TransportFormatSet-ExtIEs} }		OPTIONAL,
	...
}

TransportFormatSet-ExtIEs NBAP-PROTOCOL-EXTENSION ::= {
	...
}

TransportFormatSet-DynamicPartList ::= SEQUENCE (SIZE (1..maxNrOfTFs)) OF
	SEQUENCE {
		nrOfTransportBlocks			TransportFormatSet-NrOfTransportBlocks,
		transportBlockSize			TransportFormatSet-TransportBlockSize		OPTIONAL,
		-- This IE shall be present if the Number of Transport Blocks IE is set to a value greater than 0
		mode						TransportFormatSet-ModeDP,
		iE-Extensions				ProtocolExtensionContainer  { { TransportFormatSet-DynamicPartList-ExtIEs} }		OPTIONAL,
		...
	}

TransportFormatSet-DynamicPartList-ExtIEs NBAP-PROTOCOL-EXTENSION ::= {
	...
}

TDD-TransportFormatSet-ModeDP ::= SEQUENCE {
	transmissionTimeIntervalInformation		TransmissionTimeIntervalInformation		OPTIONAL,
	-- This IE shall be present if the Transmission Time Interval IE in the Semi-static Transport Format Information IE is set to “dynamic”
	iE-Extensions							ProtocolExtensionContainer { {TDD-TransportFormatSet-ModeDP-ExtIEs} } OPTIONAL,
	...
	}

TDD-TransportFormatSet-ModeDP-ExtIEs NBAP-PROTOCOL-EXTENSION ::= {
	...
}

TransmissionTimeIntervalInformation ::= SEQUENCE (SIZE (1..maxTTI-count)) OF
	SEQUENCE {
		transmissionTimeInterval		TransportFormatSet-TransmissionTimeIntervalDynamic,
	iE-Extensions						ProtocolExtensionContainer { { TransmissionTimeIntervalInformation-ExtIEs} }		OPTIONAL,
	...
}

TransmissionTimeIntervalInformation-ExtIEs NBAP-PROTOCOL-EXTENSION ::= {
	...
}

TransportFormatSet-Semi-staticPart ::= SEQUENCE {
	transmissionTimeInterval	 		TransportFormatSet-TransmissionTimeIntervalSemiStatic,
	channelCoding					TransportFormatSet-ChannelCodingType,
	codingRate						TransportFormatSet-CodingRate				OPTIONAL,
	-- This IE shall be present if the Type of channel coding IE is set to 'convolutional' or 'turbo' 
	rateMatchingAttribute			TransportFormatSet-RateMatchingAttribute,
	cRC-Size						TransportFormatSet-CRC-Size,
	mode							TransportFormatSet-ModeSSP	,
	iE-Extensions					ProtocolExtensionContainer { { TransportFormatSet-Semi-staticPart-ExtIEs} }		OPTIONAL,
	...
}

TransportFormatSet-Semi-staticPart-ExtIEs NBAP-PROTOCOL-EXTENSION ::= {
	...
}

TransportFormatSet-ChannelCodingType ::= ENUMERATED {
	no-codingTDD,
	convolutional-coding,
	turbo-coding,
	...
}

TransportFormatSet-CodingRate ::= ENUMERATED {
	half,
	third,
	...
}

TransportFormatSet-CRC-Size ::= ENUMERATED {
	v0,
	v8,
	v12,
	v16,
	v24,
	...
}

TransportFormatSet-ModeDP ::= CHOICE {
	tdd 				TDD-TransportFormatSet-ModeDP,
	notApplicable				NULL,
	...
}

TransportFormatSet-ModeSSP ::= CHOICE {
	tdd				TransportFormatSet-SecondInterleavingMode,
	notApplicable				NULL,
	...
}

TransportFormatSet-NrOfTransportBlocks ::= INTEGER (0..512)

TransportFormatSet-RateMatchingAttribute ::= INTEGER (1..maxRateMatching)

TransportFormatSet-SecondInterleavingMode ::= ENUMERATED {
	frame-rlated,
	timeSlot-related,
	...
}

TransportFormatSet-TransmissionTimeIntervalDynamic ::= ENUMERATED {
	msec-10,
	msec-20,
	msec-40,
	msec-80,
	...
}

TransportFormatSet-TransmissionTimeIntervalSemiStatic ::= ENUMERATED {
	msec-10,
	msec-20,
	msec-40,
	msec-80,
	dynamic,
	...,
	msec-5
}

TransportFormatSet-TransportBlockSize ::= INTEGER (0..5000)

TransportLayerAddress ::= BIT STRING (SIZE (1..160, ...))

TSTD-Indicator ::= ENUMERATED {
	active,
	inactive
}

TUTRANGPS ::= SEQUENCE {
	ms-part 	INTEGER (0..16383),
	ls-part		INTEGER (0..4294967295)
}

TUTRANGPSChangeLimit ::= INTEGER (1..256)
-- Unit chip, Step 1/16 chip, Range 1/16..16 chip

TUTRANGPSDriftRate ::= INTEGER (-50..50)
-- Unit chip/s, Step 1/256 chip/s, Range -50/256..+50/256 chip/s

TUTRANGPSDriftRateQuality ::= INTEGER (0..50)
-- Unit chip/s, Step 1/256 chip/s, Range 0..50/256 chip/s

TUTRANGPSAccuracyClass ::= ENUMERATED {
	accuracy-class-A,
	accuracy-class-B,
	accuracy-class-C,
	...
}

TUTRANGPSMeasurementThresholdInformation ::= SEQUENCE {
	tUTRANGPSChangeLimit					TUTRANGPSChangeLimit					OPTIONAL,
	predictedTUTRANGPSDeviationLimit		PredictedTUTRANGPSDeviationLimit		OPTIONAL,
	iE-Extensions					ProtocolExtensionContainer { { TUTRANGPSMeasurementThresholdInformation-ExtIEs} }		OPTIONAL,
	...
}

TUTRANGPSMeasurementThresholdInformation-ExtIEs NBAP-PROTOCOL-EXTENSION ::= {
	...
}

TUTRANGPSMeasurementValueInformation ::= SEQUENCE {
		tUTRANGPS						TUTRANGPS,
		tUTRANGPSQuality				TUTRANGPSQuality				OPTIONAL,
		tUTRANGPSDriftRate				TUTRANGPSDriftRate,
		tUTRANGPSDriftRateQuality		TUTRANGPSDriftRateQuality		OPTIONAL,
		iE-Extensions					ProtocolExtensionContainer { {TUTRANGPSMeasurementValueInformationItem-ExtIEs} }		OPTIONAL,
		...
}

TUTRANGPSMeasurementValueInformationItem-ExtIEs NBAP-PROTOCOL-EXTENSION ::= {
	...
}

TUTRANGPSQuality ::= INTEGER (0..255)
-- Unit chip, Step 1/16 chip, Range 0.. 255/16 chip

TypeOfError ::= ENUMERATED {
	not-understood,
	missing,
	...
}

-- ==========================================
--	U
-- ==========================================

UARFCN ::= INTEGER (0..16383, ...)
-- corresponds to 1885.2MHz .. 2024.8MHz

UC-Id ::= SEQUENCE {
	rNC-ID				RNC-ID,
	c-ID				C-ID,
	iE-Extensions			ProtocolExtensionContainer { {UC-Id-ExtIEs} } OPTIONAL,
	...
}
UC-Id-ExtIEs NBAP-PROTOCOL-EXTENSION ::= {
	...
}

UDRE ::= ENUMERATED {
    udre-minusequal-one-m,
    udre-betweenoneandfour-m,
    udre-betweenfourandeight-m,
    udre-greaterequaleight-m
}

UE-Capability-InformationFDD ::= SEQUENCE {
	hSDSCH-TrCH-Bits-Per-HSDSCH-TTI			ENUMERATED {v7300, v14600, v20456, v28800,...},
	hSDSCH-Multi-Code-Capability			ENUMERATED {v5, v10, v15,...},
	min-Inter-TTI-Interval					INTEGER (1..3,...),
	mAChs-Reordering-Buffer-Size			INTEGER (1..300,...),
	iE-Extensions						ProtocolExtensionContainer { { UE-Capability-InformationFDD-ExtIEs } }			OPTIONAL,
	...
}

UE-Capability-InformationFDD-ExtIEs NBAP-PROTOCOL-EXTENSION ::= {
	...
}

UE-Capability-InformationTDD ::= SEQUENCE {
	hsDSCHTrCHBitsPerTTI					ENUMERATED { v7040, v10228, v14080, ... },
	hSDSCH-Multi-Code-Capability			ENUMERATED {v8, v12, v16,...},
	mAChs-Reordering-Buffer-Size			INTEGER (1..300,...),
	iE-Extensions						ProtocolExtensionContainer { { UE-Capability-InformationTDD-ExtIEs } }			OPTIONAL,
	...
}

UE-Capability-InformationTDD-ExtIEs NBAP-PROTOCOL-EXTENSION ::= {
	...
}

UL-CapacityCredit ::= INTEGER (0..65535)

UL-DL-mode ::= ENUMERATED {
	ul-only,
	dl-only,
	both-ul-and-dl
}

Uplink-Compressed-Mode-Method 	::= ENUMERATED {
	sFdiv2,
	higher-layer-scheduling,
	...
}

UL-Timeslot-Information ::= SEQUENCE (SIZE (1..maxNrOfULTSs)) OF UL-Timeslot-InformationItem

UL-Timeslot-InformationItem ::= SEQUENCE {
	timeSlot								TimeSlot,
	midambleShiftAndBurstType				MidambleShiftAndBurstType,
	tFCI-Presence							TFCI-Presence,
	uL-Code-InformationList					TDD-UL-Code-Information,
	iE-Extensions							ProtocolExtensionContainer { { UL-Timeslot-InformationItem-ExtIEs} }		OPTIONAL,
	...
}

UL-Timeslot-InformationItem-ExtIEs NBAP-PROTOCOL-EXTENSION ::= {
	...
}

UL-TimeslotLCR-Information ::= SEQUENCE (SIZE (1..maxNrOfULTSLCRs)) OF UL-TimeslotLCR-InformationItem

UL-TimeslotLCR-InformationItem ::= SEQUENCE {
	timeSlotLCR								TimeSlotLCR,
	midambleShiftLCR						MidambleShiftLCR,
	tFCI-Presence							TFCI-Presence,
	uL-Code-InformationList					TDD-UL-Code-LCR-Information,
	iE-Extensions							ProtocolExtensionContainer { { UL-TimeslotLCR-InformationItem-ExtIEs} }		OPTIONAL,
	...
}

UL-TimeslotLCR-InformationItem-ExtIEs NBAP-PROTOCOL-EXTENSION ::= {
	...
}

UL-DPCCH-SlotFormat ::= INTEGER (0..5,...)

UL-SIR ::= INTEGER (-82..173)
-- According to mapping in [16]

UL-FP-Mode ::= ENUMERATED {
	normal,
	silent,
	...
}

UL-PhysCH-SF-Variation ::= ENUMERATED {
	sf-variation-supported,
	sf-variation-not-supported
}

UL-ScramblingCode ::= SEQUENCE {
	uL-ScramblingCodeNumber			UL-ScramblingCodeNumber,
	uL-ScramblingCodeLength			UL-ScramblingCodeLength,
	iE-Extensions					ProtocolExtensionContainer { { UL-ScramblingCode-ExtIEs } }		OPTIONAL,
	...
}

UL-ScramblingCode-ExtIEs NBAP-PROTOCOL-EXTENSION ::= {
	...
}

UL-ScramblingCodeNumber ::= INTEGER (0..16777215)

UL-ScramblingCodeLength ::= ENUMERATED {
	short,
	long
}

UL-Synchronisation-Parameters-LCR ::= SEQUENCE {
	uL-Synchronisation-StepSize			UL-Synchronisation-StepSize,
	uL-Synchronisation-Frequency		UL-Synchronisation-Frequency,
	iE-Extensions						ProtocolExtensionContainer { { UL-Synchronisation-Parameters-LCR-ExtIEs } }		OPTIONAL,
	...
}

UL-Synchronisation-Parameters-LCR-ExtIEs NBAP-PROTOCOL-EXTENSION ::= {
	...
}

UL-Synchronisation-StepSize ::= INTEGER (1..8)

UL-Synchronisation-Frequency ::= INTEGER (1..8)

UL-TimeSlot-ISCP-Info ::= SEQUENCE (SIZE (1..maxNrOfULTSs)) OF	UL-TimeSlot-ISCP-InfoItem

UL-TimeSlot-ISCP-InfoItem ::= SEQUENCE {
 	timeSlot						TimeSlot,
	iSCP							UL-TimeslotISCP-Value,
	iE-Extensions					ProtocolExtensionContainer { { UL-TimeSlot-ISCP-InfoItem-ExtIEs} }		OPTIONAL,
	...
 }

UL-TimeSlot-ISCP-InfoItem-ExtIEs NBAP-PROTOCOL-EXTENSION ::= {
	...
}

UL-TimeSlot-ISCP-LCR-Info ::= SEQUENCE (SIZE (1..maxNrOfULTSLCRs)) OF	UL-TimeSlot-ISCP-LCR-InfoItem

UL-TimeSlot-ISCP-LCR-InfoItem ::= SEQUENCE {
 	timeSlotLCR						TimeSlotLCR,
	iSCP							UL-TimeslotISCP-Value,
	iE-Extensions					ProtocolExtensionContainer { { UL-TimeSlot-ISCP-LCR-InfoItem-ExtIEs} }		OPTIONAL,
	...
 }

UL-TimeSlot-ISCP-LCR-InfoItem-ExtIEs NBAP-PROTOCOL-EXTENSION ::= {
	...
}

USCH-Information ::= SEQUENCE (SIZE (1..maxNrOfUSCHs)) OF USCH-InformationItem

USCH-InformationItem ::= SEQUENCE {
	uSCH-ID									USCH-ID,
	cCTrCH-ID								CCTrCH-ID,
	transportFormatSet						TransportFormatSet,
	allocationRetentionPriority				AllocationRetentionPriority,
	iE-Extensions							ProtocolExtensionContainer { { USCH-InformationItem-ExtIEs} }		OPTIONAL,
	...
}

USCH-InformationItem-ExtIEs NBAP-PROTOCOL-EXTENSION ::= {
	{ ID id-bindingID						CRITICALITY	ignore		EXTENSION 	BindingID				PRESENCE 	optional	}|
	{ ID id-transportlayeraddress			CRITICALITY	ignore		EXTENSION 	TransportLayerAddress		PRESENCE 	optional	},
	...
}

USCH-InformationResponse ::= SEQUENCE (SIZE (1..maxNrOfUSCHs)) OF USCH-InformationResponseItem

USCH-InformationResponseItem ::= SEQUENCE {
	uSCH-ID										USCH-ID,
	bindingID									BindingID				OPTIONAL,
	transportLayerAddress						TransportLayerAddress	OPTIONAL,
	iE-Extensions								ProtocolExtensionContainer { { USCH-InformationResponseItem-ExtIEs} }		OPTIONAL,
	...
}

USCH-InformationResponseItem-ExtIEs NBAP-PROTOCOL-EXTENSION ::= {
	...
}

UL-TimeslotISCP-Value ::= INTEGER (0..127)
-- According to mapping in [23]

UL-TimeslotISCP-Value-IncrDecrThres ::= INTEGER (0..126)

USCH-ID ::= INTEGER (0..255)

-- ==========================================
--	V
-- ==========================================

-- ==========================================
--	W
-- ==========================================

-- ==========================================
--	X
-- ==========================================

-- ==========================================
--	Y
-- ==========================================

-- ==========================================
--	Z
-- ==========================================

END

-- **************************************************************
--
-- Common definitions
--
-- **************************************************************

NBAP-CommonDataTypes {
itu-t (0) identified-organization (4) etsi (0) mobileDomain (0) 
umts-Access (20) modules (3) nbap (2) version1 (1) nbap-CommonDataTypes (3)  }

DEFINITIONS AUTOMATIC TAGS ::= 

BEGIN

-- **************************************************************
--
-- Extension constants
--
-- **************************************************************

maxPrivateIEs 					INTEGER ::= 65535
maxProtocolExtensions 			INTEGER ::= 65535
maxProtocolIEs					INTEGER ::= 65535

-- **************************************************************
--
-- Common Data Types
--
-- **************************************************************

Criticality		::= ENUMERATED { reject, ignore, notify }

MessageDiscriminator	::= ENUMERATED { common, dedicated }

Presence		::= ENUMERATED { optional, conditional, mandatory }

PrivateIE-ID	::= CHOICE {
	local				INTEGER (0..maxPrivateIEs),
	global				OBJECT IDENTIFIER
}

ProcedureCode	::= INTEGER (0..255)

ProcedureID		::= SEQUENCE {
	procedureCode			ProcedureCode,
	ddMode				ENUMERATED { tdd, fdd, common, ... }
}

ProtocolIE-ID		::= INTEGER (0..maxProtocolIEs)

TransactionID 		::= CHOICE {
	shortTransActionId		INTEGER (0..127),
	longTransActionId		INTEGER (0..32767)
}

TriggeringMessage	::= ENUMERATED { initiating-message, successful-outcome, unsuccessfull-outcome, outcome }

END

-- **************************************************************
--
-- Constant definitions
--
-- **************************************************************

NBAP-Constants {
itu-t (0) identified-organization (4) etsi (0) mobileDomain (0) 
umts-Access (20) modules (3) nbap (2) version1 (1) nbap-Constants (4)}

DEFINITIONS AUTOMATIC TAGS ::= 

BEGIN

IMPORTS
	ProcedureCode,
	ProtocolIE-ID
FROM NBAP-CommonDataTypes;

-- **************************************************************
--
-- Elementary Procedures
--
-- **************************************************************

id-audit 												ProcedureCode ::= 0
id-auditRequired 										ProcedureCode ::= 1
id-blockResource 										ProcedureCode ::= 2
id-cellDeletion 										ProcedureCode ::= 3
id-cellReconfiguration 									ProcedureCode ::= 4
id-cellSetup 											ProcedureCode ::= 5
id-cellSynchronisationInitiation						ProcedureCode ::= 45
id-cellSynchronisationReconfiguration					ProcedureCode ::= 46
id-cellSynchronisationReporting							ProcedureCode ::= 47
id-cellSynchronisationTermination						ProcedureCode ::= 48
id-cellSynchronisationFailure							ProcedureCode ::= 49
id-commonMeasurementFailure 							ProcedureCode ::= 6
id-commonMeasurementInitiation 							ProcedureCode ::= 7
id-commonMeasurementReport 								ProcedureCode ::= 8
id-commonMeasurementTermination 						ProcedureCode ::= 9
id-commonTransportChannelDelete 						ProcedureCode ::= 10
id-commonTransportChannelReconfigure 					ProcedureCode ::= 11
id-commonTransportChannelSetup 							ProcedureCode ::= 12
id-compressedModeCommand 								ProcedureCode ::= 14
id-dedicatedMeasurementFailure 							ProcedureCode ::= 16
id-dedicatedMeasurementInitiation 						ProcedureCode ::= 17
id-dedicatedMeasurementReport 							ProcedureCode ::= 18
id-dedicatedMeasurementTermination 						ProcedureCode ::= 19
id-downlinkPowerControl 								ProcedureCode ::= 20
id-downlinkPowerTimeslotControl 						ProcedureCode ::= 38
id-errorIndicationForCommon								ProcedureCode ::= 35
id-errorIndicationForDedicated							ProcedureCode ::= 21
id-informationExchangeFailure							ProcedureCode ::= 40
id-informationExchangeInitiation						ProcedureCode ::= 41
id-informationExchangeTermination						ProcedureCode ::= 42
id-informationReporting									ProcedureCode ::= 43
id-BearerRearrangement									ProcedureCode ::= 50
id-physicalSharedChannelReconfiguration 				ProcedureCode ::= 37
id-privateMessageForCommon								ProcedureCode ::= 36
id-privateMessageForDedicated							ProcedureCode ::= 22
id-radioLinkAddition 									ProcedureCode ::= 23
id-radioLinkDeletion 									ProcedureCode ::= 24
id-radioLinkFailure 									ProcedureCode ::= 25
id-radioLinkPreemption									ProcedureCode ::= 39
id-radioLinkRestoration 								ProcedureCode ::= 26
id-radioLinkSetup 										ProcedureCode ::= 27
id-reset												ProcedureCode ::= 13
id-resourceStatusIndication 							ProcedureCode ::= 28
id-cellSynchronisationAdjustment						ProcedureCode ::= 44
id-synchronisedRadioLinkReconfigurationCancellation		ProcedureCode ::= 29
id-synchronisedRadioLinkReconfigurationCommit			ProcedureCode ::= 30
id-synchronisedRadioLinkReconfigurationPreparation 		ProcedureCode ::= 31
id-systemInformationUpdate 								ProcedureCode ::= 32
id-unblockResource 										ProcedureCode ::= 33
id-unSynchronisedRadioLinkReconfiguration 				ProcedureCode ::= 34
id-radioLinkActivation									ProcedureCode ::= 51
id-radioLinkParameterUpdate								ProcedureCode ::= 52

-- **************************************************************
--
-- Lists
--
-- **************************************************************

maxNrOfCodes				INTEGER ::= 10
maxNrOfDLTSs				INTEGER ::= 15
maxNrOfDLTSLCRs				INTEGER ::= 6
maxNrOfErrors				INTEGER ::= 256
maxNrOfTFs					INTEGER ::= 32
maxNrOfTFCs					INTEGER ::= 1024
maxNrOfRLs					INTEGER ::= 16
maxNrOfRLs-1				INTEGER ::= 15	-- maxNrOfRLs – 1
maxNrOfRLs-2				INTEGER ::= 14	-- maxNrOfRLs – 2
maxNrOfRLSets				INTEGER ::= maxNrOfRLs
maxNrOfDPCHs				INTEGER ::= 240
maxNrOfDPCHLCRs				INTEGER ::= 240
maxNrOfSCCPCHs				INTEGER ::= 8
maxNrOfCPCHs				INTEGER ::= 16
maxNrOfPCPCHs				INTEGER ::= 64
maxNrOfDCHs					INTEGER ::= 128
maxNrOfDSCHs				INTEGER ::= 32
maxNrOfFACHs				INTEGER ::= 8
maxNrOfCCTrCHs				INTEGER ::= 16
maxNrOfPDSCHs				INTEGER ::= 256
maxNrOfPUSCHs				INTEGER ::= 256
maxNrOfPDSCHSets			INTEGER ::= 256
maxNrOfPRACHLCRs			INTEGER ::= 8
maxNrOfPUSCHSets			INTEGER ::= 256
maxNrOfSCCPCHLCRs			INTEGER ::= 8
maxNrOfULTSs				INTEGER ::= 15
maxNrOfULTSLCRs				INTEGER ::= 6
maxNrOfUSCHs				INTEGER ::= 32
maxAPSigNum					INTEGER ::= 16
maxNrOfSlotFormatsPRACH		INTEGER ::= 8
maxCellinNodeB				INTEGER ::= 256
maxCCPinNodeB				INTEGER ::= 256
maxCPCHCell					INTEGER ::= maxNrOfCPCHs
maxCTFC						INTEGER ::= 16777215
maxLocalCellinNodeB			INTEGER ::= maxCellinNodeB
maxNoofLen					INTEGER ::= 7
maxFPACHCell				INTEGER ::= 8
maxRACHCell					INTEGER ::= maxPRACHCell
maxPRACHCell				INTEGER ::= 16
maxPCPCHCell				INTEGER ::= 64
maxSCCPCHCell				INTEGER ::= 32
maxSCPICHCell				INTEGER ::= 32
maxTTI-count				INTEGER ::= 4
maxIBSEG					INTEGER ::= 16
maxIB						INTEGER ::= 64
maxFACHCell 				INTEGER ::= 256	-- maxNrOfFACHs * maxSCCPCHCell
maxRateMatching				INTEGER ::= 256
maxCodeNrComp-1				INTEGER ::= 256
maxNrOfCellSyncBursts		INTEGER	::=	10
maxNrOfCodeGroups			INTEGER ::= 256
maxNrOfReceptsPerSyncFrame	INTEGER	::=	16
maxNrOfMeasNCell			INTEGER ::= 96
maxNrOfMeasNCell-1			INTEGER ::= 95	-- maxNrOfMeasNCell – 1
maxNrOfTFCIGroups			INTEGER ::= 256
maxNrOfTFCI1Combs			INTEGER ::= 512
maxNrOfTFCI2Combs			INTEGER ::= 1024
maxNrOfTFCI2Combs-1			INTEGER ::= 1023
maxNrOfSF					INTEGER ::= 8
maxTGPS						INTEGER ::= 6
maxCommunicationContext		INTEGER ::= 1048575
maxNrOfLevels				INTEGER ::= 256
maxNoSat                    INTEGER ::= 16
maxNoGPSItems               INTEGER ::= 8
maxNrOfHSSCCHs				INTEGER ::= 32
maxNrOfSyncFramesLCR		INTEGER ::=	512
maxNrOfReceptionsperSyncFrameLCR	INTEGER ::=	8
maxNrOfSyncDLCodesLCR		INTEGER ::= 32
maxNrOfHSSCCHCodes			INTEGER ::= 4
maxNrOfMACdFlows			INTEGER ::= 8
maxNrOfMACdFlows-1			INTEGER ::= 7	-- maxNrOfMACdFlows - 1
maxNrOfMACdPDUIndexes		INTEGER ::= 8
maxNrOfMACdPDUIndexes-1		INTEGER ::= 7	-- maxNoOfMACdPDUIndexes - 1
maxNrOfPriorityQueues		INTEGER ::= 8
maxNrOfPriorityQueues-1		INTEGER ::= 7	-- maxNoOfPriorityQueues - 1
maxNrOfHARQProcesses		INTEGER ::= 8

-- **************************************************************
--
-- IEs
--
-- **************************************************************

id-AICH-Information													ProtocolIE-ID ::= 0
id-AICH-InformationItem-ResourceStatusInd							ProtocolIE-ID ::= 1
id-BCH-Information													ProtocolIE-ID ::= 7
id-BCH-InformationItem-ResourceStatusInd							ProtocolIE-ID ::= 8
id-BCCH-ModificationTime											ProtocolIE-ID ::= 9
id-BlockingPriorityIndicator										ProtocolIE-ID ::= 10
id-Cause															ProtocolIE-ID ::= 13
id-CCP-InformationItem-AuditRsp										ProtocolIE-ID ::= 14
id-CCP-InformationList-AuditRsp										ProtocolIE-ID ::= 15
id-CCP-InformationItem-ResourceStatusInd							ProtocolIE-ID ::= 16
id-Cell-InformationItem-AuditRsp									ProtocolIE-ID ::= 17
id-Cell-InformationItem-ResourceStatusInd							ProtocolIE-ID ::= 18
id-Cell-InformationList-AuditRsp									ProtocolIE-ID ::= 19
id-CellParameterID													ProtocolIE-ID ::= 23
id-CFN																ProtocolIE-ID ::= 24
id-C-ID																	ProtocolIE-ID ::= 25
id-CommonMeasurementAccuracy										ProtocolIE-ID ::= 39
id-CommonMeasurementObjectType-CM-Rprt								ProtocolIE-ID ::= 31
id-CommonMeasurementObjectType-CM-Rqst								ProtocolIE-ID ::= 32
id-CommonMeasurementObjectType-CM-Rsp								ProtocolIE-ID ::= 33
id-CommonMeasurementType											ProtocolIE-ID ::= 34
id-CommonPhysicalChannelID											ProtocolIE-ID ::= 35
id-CommonPhysicalChannelType-CTCH-SetupRqstFDD						ProtocolIE-ID ::= 36
id-CommonPhysicalChannelType-CTCH-SetupRqstTDD						ProtocolIE-ID ::= 37
id-CommunicationControlPortID										ProtocolIE-ID ::= 40
id-ConfigurationGenerationID										ProtocolIE-ID ::= 43
id-CRNC-CommunicationContextID										ProtocolIE-ID ::= 44
id-CriticalityDiagnostics											ProtocolIE-ID ::= 45
id-DCHs-to-Add-FDD													ProtocolIE-ID ::= 48
id-DCH-AddList-RL-ReconfPrepTDD										ProtocolIE-ID ::= 49
id-DCHs-to-Add-TDD													ProtocolIE-ID ::= 50
id-DCH-DeleteList-RL-ReconfPrepFDD									ProtocolIE-ID ::= 52
id-DCH-DeleteList-RL-ReconfPrepTDD									ProtocolIE-ID ::= 53
id-DCH-DeleteList-RL-ReconfRqstFDD									ProtocolIE-ID ::= 54
id-DCH-DeleteList-RL-ReconfRqstTDD									ProtocolIE-ID ::= 55
id-DCH-FDD-Information												ProtocolIE-ID ::= 56
id-DCH-TDD-Information												ProtocolIE-ID ::= 57
id-DCH-InformationResponse											ProtocolIE-ID ::= 59
id-FDD-DCHs-to-Modify												ProtocolIE-ID ::= 62
id-TDD-DCHs-to-Modify												ProtocolIE-ID ::= 63
id-DCH-ModifyList-RL-ReconfRqstTDD									ProtocolIE-ID ::= 65
id-DCH-RearrangeList-Bearer-RearrangeInd							ProtocolIE-ID ::= 135
id-DedicatedMeasurementObjectType-DM-Rprt							ProtocolIE-ID ::= 67
id-DedicatedMeasurementObjectType-DM-Rqst							ProtocolIE-ID ::= 68
id-DedicatedMeasurementObjectType-DM-Rsp							ProtocolIE-ID ::= 69
id-DedicatedMeasurementType											ProtocolIE-ID ::= 70
id-DL-CCTrCH-InformationItem-RL-SetupRqstTDD						ProtocolIE-ID ::= 72
id-DL-CCTrCH-InformationList-RL-AdditionRqstTDD						ProtocolIE-ID ::= 73
id-DL-CCTrCH-InformationList-RL-SetupRqstTDD						ProtocolIE-ID ::= 76
id-DL-DPCH-InformationItem-RL-AdditionRqstTDD						ProtocolIE-ID ::= 77
id-DL-DPCH-InformationList-RL-SetupRqstTDD							ProtocolIE-ID ::= 79
id-DL-DPCH-Information-RL-ReconfPrepFDD								ProtocolIE-ID ::= 81
id-DL-DPCH-Information-RL-ReconfRqstFDD								ProtocolIE-ID ::= 82
id-DL-DPCH-Information-RL-SetupRqstFDD								ProtocolIE-ID ::= 83
id-DL-DPCH-TimingAdjustment											ProtocolIE-ID ::= 21
id-DL-ReferencePowerInformationItem-DL-PC-Rqst						ProtocolIE-ID ::= 84
id-DLReferencePower													ProtocolIE-ID ::= 85
id-DLReferencePowerList-DL-PC-Rqst									ProtocolIE-ID ::= 86
id-DSCH-AddItem-RL-ReconfPrepFDD									ProtocolIE-ID ::= 87
id-DSCHs-to-Add-FDD													ProtocolIE-ID ::= 89
id-DSCH-DeleteItem-RL-ReconfPrepFDD									ProtocolIE-ID ::= 91
id-DSCH-DeleteList-RL-ReconfPrepFDD									ProtocolIE-ID ::= 93
id-DSCHs-to-Add-TDD													ProtocolIE-ID ::= 96
id-DSCH-Information-DeleteList-RL-ReconfPrepTDD						ProtocolIE-ID ::= 98
id-DSCH-Information-ModifyList-RL-ReconfPrepTDD						ProtocolIE-ID ::= 100
id-DSCH-InformationResponse											ProtocolIE-ID ::= 105
id-DSCH-FDD-Information												ProtocolIE-ID ::= 106
id-DSCH-TDD-Information												ProtocolIE-ID ::= 107
id-DSCH-ModifyItem-RL-ReconfPrepFDD									ProtocolIE-ID ::= 108
id-DSCH-ModifyList-RL-ReconfPrepFDD									ProtocolIE-ID ::= 112
id-DSCH-RearrangeList-Bearer-RearrangeInd							ProtocolIE-ID ::= 136
id-End-Of-Audit-Sequence-Indicator 									ProtocolIE-ID ::= 113
id-FACH-Information													ProtocolIE-ID ::= 116
id-FACH-InformationItem-ResourceStatusInd							ProtocolIE-ID ::= 117
id-FACH-ParametersList-CTCH-ReconfRqstTDD							ProtocolIE-ID ::= 120
id-FACH-ParametersListIE-CTCH-SetupRqstFDD							ProtocolIE-ID ::= 121
id-FACH-ParametersListIE-CTCH-SetupRqstTDD							ProtocolIE-ID ::= 122
id-IndicationType-ResourceStatusInd									ProtocolIE-ID ::= 123
id-Local-Cell-ID													ProtocolIE-ID ::= 124
id-Local-Cell-Group-InformationItem-AuditRsp						ProtocolIE-ID ::= 2
id-Local-Cell-Group-InformationItem-ResourceStatusInd				ProtocolIE-ID ::= 3
id-Local-Cell-Group-InformationItem2-ResourceStatusInd				ProtocolIE-ID ::= 4
id-Local-Cell-Group-InformationList-AuditRsp						ProtocolIE-ID ::= 5
id-Local-Cell-InformationItem-AuditRsp								ProtocolIE-ID ::= 125
id-Local-Cell-InformationItem-ResourceStatusInd						ProtocolIE-ID ::= 126
id-Local-Cell-InformationItem2-ResourceStatusInd					ProtocolIE-ID ::= 127
id-Local-Cell-InformationList-AuditRsp								ProtocolIE-ID ::= 128
id-AdjustmentPeriod													ProtocolIE-ID ::= 129
id-MaxAdjustmentStep												ProtocolIE-ID ::= 130
id-MaximumTransmissionPower											ProtocolIE-ID ::= 131
id-MeasurementFilterCoefficient										ProtocolIE-ID ::= 132
id-MeasurementID													ProtocolIE-ID ::= 133
id-MessageStructure													ProtocolIE-ID ::= 115
id-MIB-SB-SIB-InformationList-SystemInfoUpdateRqst					ProtocolIE-ID ::= 134
id-NodeB-CommunicationContextID										ProtocolIE-ID ::= 143
id-NeighbouringCellMeasurementInformation							ProtocolIE-ID ::= 455
id-P-CCPCH-Information												ProtocolIE-ID ::= 144
id-P-CCPCH-InformationItem-ResourceStatusInd						ProtocolIE-ID ::= 145
id-P-CPICH-Information												ProtocolIE-ID ::= 146
id-P-CPICH-InformationItem-ResourceStatusInd						ProtocolIE-ID ::= 147
id-P-SCH-Information												ProtocolIE-ID ::= 148
id-PCCPCH-Information-Cell-ReconfRqstTDD							ProtocolIE-ID ::= 150
id-PCCPCH-Information-Cell-SetupRqstTDD								ProtocolIE-ID ::= 151
id-PCH-Parameters-CTCH-ReconfRqstTDD								ProtocolIE-ID ::= 155
id-PCH-ParametersItem-CTCH-SetupRqstFDD								ProtocolIE-ID ::= 156
id-PCH-ParametersItem-CTCH-SetupRqstTDD								ProtocolIE-ID ::= 157
id-PCH-Information													ProtocolIE-ID ::= 158
id-PDSCH-Information-AddListIE-PSCH-ReconfRqst						ProtocolIE-ID ::= 161
id-PDSCH-Information-ModifyListIE-PSCH-ReconfRqst					ProtocolIE-ID ::= 162
id-PDSCHSets-AddList-PSCH-ReconfRqst								ProtocolIE-ID ::= 163
id-PDSCHSets-DeleteList-PSCH-ReconfRqst								ProtocolIE-ID ::= 164
id-PDSCHSets-ModifyList-PSCH-ReconfRqst								ProtocolIE-ID ::= 165
id-PICH-Information													ProtocolIE-ID ::= 166
id-PICH-Parameters-CTCH-ReconfRqstTDD								ProtocolIE-ID ::= 168
id-PowerAdjustmentType												ProtocolIE-ID ::= 169
id-PRACH-Information												ProtocolIE-ID ::= 170
id-PrimaryCCPCH-Information-Cell-ReconfRqstFDD						ProtocolIE-ID ::= 175
id-PrimaryCCPCH-Information-Cell-SetupRqstFDD						ProtocolIE-ID ::= 176
id-PrimaryCPICH-Information-Cell-ReconfRqstFDD						ProtocolIE-ID ::= 177
id-PrimaryCPICH-Information-Cell-SetupRqstFDD						ProtocolIE-ID ::= 178
id-PrimarySCH-Information-Cell-ReconfRqstFDD						ProtocolIE-ID ::= 179
id-PrimarySCH-Information-Cell-SetupRqstFDD							ProtocolIE-ID ::= 180
id-PrimaryScramblingCode											ProtocolIE-ID ::= 181
id-SCH-Information-Cell-ReconfRqstTDD								ProtocolIE-ID ::= 183
id-SCH-Information-Cell-SetupRqstTDD								ProtocolIE-ID ::= 184
id-PUSCH-Information-AddListIE-PSCH-ReconfRqst						ProtocolIE-ID ::= 185
id-PUSCH-Information-ModifyListIE-PSCH-ReconfRqst					ProtocolIE-ID ::= 186
id-PUSCHSets-AddList-PSCH-ReconfRqst								ProtocolIE-ID ::= 187
id-PUSCHSets-DeleteList-PSCH-ReconfRqst								ProtocolIE-ID ::= 188
id-PUSCHSets-ModifyList-PSCH-ReconfRqst								ProtocolIE-ID ::= 189
id-RACH-Information													ProtocolIE-ID ::= 190
id-RACH-ParametersItem-CTCH-SetupRqstFDD							ProtocolIE-ID ::= 196
id-RACH-ParameterItem-CTCH-SetupRqstTDD								ProtocolIE-ID ::= 197
id-ReportCharacteristics											ProtocolIE-ID ::= 198
id-Reporting-Object-RL-FailureInd									ProtocolIE-ID ::= 199
id-Reporting-Object-RL-RestoreInd									ProtocolIE-ID ::= 200
id-RL-InformationItem-DM-Rprt										ProtocolIE-ID ::= 202
id-RL-InformationItem-DM-Rqst										ProtocolIE-ID ::= 203
id-RL-InformationItem-DM-Rsp										ProtocolIE-ID ::= 204
id-RL-InformationItem-RL-AdditionRqstFDD							ProtocolIE-ID ::= 205
id-RL-informationItem-RL-DeletionRqst								ProtocolIE-ID ::= 206
id-RL-InformationItem-RL-FailureInd									ProtocolIE-ID ::= 207
id-RL-InformationItem-RL-PreemptRequiredInd							ProtocolIE-ID ::= 286
id-RL-InformationItem-RL-ReconfPrepFDD								ProtocolIE-ID ::= 208
id-RL-InformationItem-RL-ReconfRqstFDD								ProtocolIE-ID ::= 209
id-RL-InformationItem-RL-RestoreInd									ProtocolIE-ID ::= 210
id-RL-InformationItem-RL-SetupRqstFDD								ProtocolIE-ID ::= 211
id-RL-InformationList-RL-AdditionRqstFDD							ProtocolIE-ID ::= 212
id-RL-informationList-RL-DeletionRqst								ProtocolIE-ID ::= 213
id-RL-InformationList-RL-PreemptRequiredInd							ProtocolIE-ID ::= 237
id-RL-InformationList-RL-ReconfPrepFDD								ProtocolIE-ID ::= 214
id-RL-InformationList-RL-ReconfRqstFDD								ProtocolIE-ID ::= 215
id-RL-InformationList-RL-SetupRqstFDD								ProtocolIE-ID ::= 216
id-RL-InformationResponseItem-RL-AdditionRspFDD						ProtocolIE-ID ::= 217
id-RL-InformationResponseItem-RL-ReconfReady						ProtocolIE-ID ::= 218
id-RL-InformationResponseItem-RL-ReconfRsp							ProtocolIE-ID ::= 219
id-RL-InformationResponseItem-RL-SetupRspFDD						ProtocolIE-ID ::= 220
id-RL-InformationResponseList-RL-AdditionRspFDD						ProtocolIE-ID ::= 221
id-RL-InformationResponseList-RL-ReconfReady						ProtocolIE-ID ::= 222
id-RL-InformationResponseList-RL-ReconfRsp							ProtocolIE-ID ::= 223
id-RL-InformationResponseList-RL-SetupRspFDD						ProtocolIE-ID ::= 224
id-RL-InformationResponse-RL-AdditionRspTDD							ProtocolIE-ID ::= 225
id-RL-InformationResponse-RL-SetupRspTDD							ProtocolIE-ID ::= 226
id-RL-Information-RL-AdditionRqstTDD								ProtocolIE-ID ::= 227
id-RL-Information-RL-ReconfRqstTDD									ProtocolIE-ID ::= 228
id-RL-Information-RL-ReconfPrepTDD									ProtocolIE-ID ::= 229
id-RL-Information-RL-SetupRqstTDD									ProtocolIE-ID ::= 230
id-RL-ReconfigurationFailureItem-RL-ReconfFailure					ProtocolIE-ID ::= 236
id-RL-Set-InformationItem-DM-Rprt									ProtocolIE-ID ::= 238
id-RL-Set-InformationItem-DM-Rsp									ProtocolIE-ID ::= 240
id-RL-Set-InformationItem-RL-FailureInd								ProtocolIE-ID ::= 241
id-RL-Set-InformationItem-RL-RestoreInd								ProtocolIE-ID ::= 242
id-S-CCPCH-Information												ProtocolIE-ID ::= 247
id-S-CPICH-Information												ProtocolIE-ID ::= 249
id-SCH-Information													ProtocolIE-ID ::= 251
id-S-SCH-Information												ProtocolIE-ID ::= 253
id-Secondary-CCPCHListIE-CTCH-ReconfRqstTDD							ProtocolIE-ID ::= 257
id-Secondary-CCPCH-parameterListIE-CTCH-SetupRqstTDD				ProtocolIE-ID ::= 258
id-Secondary-CCPCH-Parameters-CTCH-ReconfRqstTDD					ProtocolIE-ID ::= 259
id-SecondaryCPICH-InformationItem-Cell-ReconfRqstFDD				ProtocolIE-ID ::= 260
id-SecondaryCPICH-InformationItem-Cell-SetupRqstFDD					ProtocolIE-ID ::= 261
id-SecondaryCPICH-InformationList-Cell-ReconfRqstFDD				ProtocolIE-ID ::= 262
id-SecondaryCPICH-InformationList-Cell-SetupRqstFDD					ProtocolIE-ID ::= 263
id-SecondarySCH-Information-Cell-ReconfRqstFDD						ProtocolIE-ID ::= 264
id-SecondarySCH-Information-Cell-SetupRqstFDD						ProtocolIE-ID ::= 265
id-SegmentInformationListIE-SystemInfoUpdate						ProtocolIE-ID ::= 266
id-SFN																ProtocolIE-ID ::= 268
id-SignallingBearerRequestIndicator									ProtocolIE-ID ::= 138
id-ShutdownTimer													ProtocolIE-ID ::= 269
id-Start-Of-Audit-Sequence-Indicator								ProtocolIE-ID ::= 114
id-Successful-RL-InformationRespItem-RL-AdditionFailureFDD			ProtocolIE-ID ::= 270
id-Successful-RL-InformationRespItem-RL-SetupFailureFDD				ProtocolIE-ID ::= 271
id-SyncCase															ProtocolIE-ID ::= 274
id-SyncCaseIndicatorItem-Cell-SetupRqstTDD-PSCH						ProtocolIE-ID ::= 275
id-T-Cell															ProtocolIE-ID ::= 276
id-TargetCommunicationControlPortID									ProtocolIE-ID ::= 139
id-TimeSlotConfigurationList-Cell-ReconfRqstTDD						ProtocolIE-ID ::= 277
id-TimeSlotConfigurationList-Cell-SetupRqstTDD						ProtocolIE-ID ::= 278
id-TransmissionDiversityApplied										ProtocolIE-ID ::= 279
id-TypeOfError														ProtocolIE-ID ::= 508
id-UARFCNforNt														ProtocolIE-ID ::= 280
id-UARFCNforNd														ProtocolIE-ID ::= 281
id-UARFCNforNu														ProtocolIE-ID ::= 282
id-UL-CCTrCH-InformationItem-RL-SetupRqstTDD						ProtocolIE-ID ::= 284
id-UL-CCTrCH-InformationList-RL-AdditionRqstTDD						ProtocolIE-ID ::= 285
id-UL-CCTrCH-InformationList-RL-SetupRqstTDD						ProtocolIE-ID ::= 288
id-UL-DPCH-InformationItem-RL-AdditionRqstTDD						ProtocolIE-ID ::= 289
id-UL-DPCH-InformationList-RL-SetupRqstTDD							ProtocolIE-ID ::= 291
id-UL-DPCH-Information-RL-ReconfPrepFDD								ProtocolIE-ID ::= 293
id-UL-DPCH-Information-RL-ReconfRqstFDD								ProtocolIE-ID ::= 294
id-UL-DPCH-Information-RL-SetupRqstFDD								ProtocolIE-ID ::= 295
id-Unsuccessful-RL-InformationRespItem-RL-AdditionFailureFDD		ProtocolIE-ID ::= 296
id-Unsuccessful-RL-InformationRespItem-RL-SetupFailureFDD			ProtocolIE-ID ::= 297
id-Unsuccessful-RL-InformationResp-RL-AdditionFailureTDD			ProtocolIE-ID ::= 300
id-Unsuccessful-RL-InformationResp-RL-SetupFailureTDD				ProtocolIE-ID ::= 301
id-USCH-Information-Add												ProtocolIE-ID ::= 302
id-USCH-Information-DeleteList-RL-ReconfPrepTDD						ProtocolIE-ID ::= 304
id-USCH-Information-ModifyList-RL-ReconfPrepTDD						ProtocolIE-ID ::= 306
id-USCH-InformationResponse											ProtocolIE-ID ::= 309
id-USCH-Information													ProtocolIE-ID ::= 310
id-USCH-RearrangeList-Bearer-RearrangeInd							ProtocolIE-ID ::= 141
id-Active-Pattern-Sequence-Information 								ProtocolIE-ID ::= 315
id-AICH-ParametersListIE-CTCH-ReconfRqstFDD							ProtocolIE-ID ::= 316
id-AdjustmentRatio													ProtocolIE-ID ::= 317
id-AP-AICH-Information												ProtocolIE-ID ::= 320
id-AP-AICH-ParametersListIE-CTCH-ReconfRqstFDD						ProtocolIE-ID ::= 322
id-FACH-ParametersListIE-CTCH-ReconfRqstFDD							ProtocolIE-ID ::= 323
id-CauseLevel-PSCH-ReconfFailure									ProtocolIE-ID ::= 324
id-CauseLevel-RL-AdditionFailureFDD									ProtocolIE-ID ::= 325
id-CauseLevel-RL-AdditionFailureTDD									ProtocolIE-ID ::= 326
id-CauseLevel-RL-ReconfFailure										ProtocolIE-ID ::= 327
id-CauseLevel-RL-SetupFailureFDD									ProtocolIE-ID ::= 328
id-CauseLevel-RL-SetupFailureTDD									ProtocolIE-ID ::= 329
id-CDCA-ICH-Information												ProtocolIE-ID ::= 330
id-CDCA-ICH-ParametersListIE-CTCH-ReconfRqstFDD						ProtocolIE-ID ::= 332
id-Closed-Loop-Timing-Adjustment-Mode								ProtocolIE-ID ::= 333
id-CommonPhysicalChannelType-CTCH-ReconfRqstFDD						ProtocolIE-ID ::= 334
id-Compressed-Mode-Deactivation-Flag								ProtocolIE-ID ::= 335
id-CPCH-Information													ProtocolIE-ID ::= 336
id-CPCH-Parameters-CTCH-SetupRsp									ProtocolIE-ID ::= 342
id-CPCH-ParametersListIE-CTCH-ReconfRqstFDD							ProtocolIE-ID ::= 343
id-DL-CCTrCH-InformationAddList-RL-ReconfPrepTDD					ProtocolIE-ID ::= 346
id-DL-CCTrCH-InformationDeleteItem-RL-ReconfRqstTDD					ProtocolIE-ID ::= 347
id-DL-CCTrCH-InformationDeleteList-RL-ReconfPrepTDD					ProtocolIE-ID ::= 348
id-DL-CCTrCH-InformationDeleteList-RL-ReconfRqstTDD					ProtocolIE-ID ::= 349
id-DL-CCTrCH-InformationModifyItem-RL-ReconfRqstTDD					ProtocolIE-ID ::= 350
id-DL-CCTrCH-InformationModifyList-RL-ReconfPrepTDD					ProtocolIE-ID ::= 351
id-DL-CCTrCH-InformationModifyList-RL-ReconfRqstTDD					ProtocolIE-ID ::= 352
id-DL-DPCH-InformationAddListIE-RL-ReconfPrepTDD					ProtocolIE-ID ::= 353
id-DL-DPCH-InformationModify-AddListIE-RL-ReconfPrepTDD				ProtocolIE-ID ::= 355
id-DL-DPCH-InformationModify-DeleteListIE-RL-ReconfPrepTDD			ProtocolIE-ID ::= 356
id-DL-DPCH-InformationModify-ModifyListIE-RL-ReconfPrepTDD			ProtocolIE-ID ::= 357
id-DL-TPC-Pattern01Count 											ProtocolIE-ID ::= 358
id-DPC-Mode															ProtocolIE-ID ::= 450
id-DPCHConstant														ProtocolIE-ID ::= 359
id-DSCH-FDD-Common-Information										ProtocolIE-ID ::= 94
id-EnhancedDSCHPC													ProtocolIE-ID ::= 110
id-EnhancedDSCHPCIndicator											ProtocolIE-ID ::= 111
id-FACH-ParametersList-CTCH-SetupRsp								ProtocolIE-ID ::= 362
id-Limited-power-increase-information-Cell-SetupRqstFDD				ProtocolIE-ID ::= 369
id-PCH-Parameters-CTCH-SetupRsp										ProtocolIE-ID ::= 374
id-PCH-ParametersItem-CTCH-ReconfRqstFDD							ProtocolIE-ID ::= 375
id-PCPCH-Information 												ProtocolIE-ID ::= 376
id-PICH-ParametersItem-CTCH-ReconfRqstFDD							ProtocolIE-ID ::= 380
id-PRACHConstant													ProtocolIE-ID ::= 381
id-PRACH-ParametersListIE-CTCH-ReconfRqstFDD						ProtocolIE-ID ::= 383
id-PUSCHConstant													ProtocolIE-ID ::= 384
id-RACH-Parameters-CTCH-SetupRsp									ProtocolIE-ID ::= 385
id-SSDT-CellIDforEDSCHPC											ProtocolIE-ID ::= 443
id-Synchronisation-Configuration-Cell-ReconfRqst					ProtocolIE-ID ::= 393
id-Synchronisation-Configuration-Cell-SetupRqst						ProtocolIE-ID ::= 394
id-Transmission-Gap-Pattern-Sequence-Information					ProtocolIE-ID ::= 395
id-UL-CCTrCH-InformationAddList-RL-ReconfPrepTDD					ProtocolIE-ID ::= 396
id-UL-CCTrCH-InformationDeleteItem-RL-ReconfRqstTDD					ProtocolIE-ID ::= 397
id-UL-CCTrCH-InformationDeleteList-RL-ReconfPrepTDD					ProtocolIE-ID ::= 398
id-UL-CCTrCH-InformationDeleteList-RL-ReconfRqstTDD					ProtocolIE-ID ::= 399
id-UL-CCTrCH-InformationModifyItem-RL-ReconfRqstTDD					ProtocolIE-ID ::= 400
id-UL-CCTrCH-InformationModifyList-RL-ReconfPrepTDD					ProtocolIE-ID ::= 401
id-UL-CCTrCH-InformationModifyList-RL-ReconfRqstTDD					ProtocolIE-ID ::= 402
id-UL-DPCH-InformationAddListIE-RL-ReconfPrepTDD					ProtocolIE-ID ::= 403
id-UL-DPCH-InformationModify-AddListIE-RL-ReconfPrepTDD				ProtocolIE-ID ::= 405
id-UL-DPCH-InformationModify-DeleteListIE-RL-ReconfPrepTDD			ProtocolIE-ID ::= 406
id-UL-DPCH-InformationModify-ModifyListIE-RL-ReconfPrepTDD			ProtocolIE-ID ::= 407
id-Unsuccessful-PDSCHSetItem-PSCH-ReconfFailureTDD					ProtocolIE-ID ::= 408
id-Unsuccessful-PUSCHSetItem-PSCH-ReconfFailureTDD					ProtocolIE-ID ::= 409
id-CommunicationContextInfoItem-Reset								ProtocolIE-ID ::= 412
id-CommunicationControlPortInfoItem-Reset							ProtocolIE-ID ::= 414
id-ResetIndicator													ProtocolIE-ID ::= 416
id-TFCI2-Bearer-Information-RL-SetupRqstFDD							ProtocolIE-ID ::= 417
id-TFCI2-BearerSpecificInformation-RL-ReconfPrepFDD					ProtocolIE-ID ::= 418
id-TFCI2-BearerInformationResponse									ProtocolIE-ID ::= 419
id-TFCI2BearerRequestIndicator										ProtocolIE-ID ::= 142
id-TimingAdvanceApplied												ProtocolIE-ID ::= 287
id-CFNReportingIndicator                                            ProtocolIE-ID ::= 6
id-SFNReportingIndicator                                            ProtocolIE-ID ::= 11
id-InnerLoopDLPCStatus												ProtocolIE-ID ::= 12
id-TimeslotISCPInfo													ProtocolIE-ID ::= 283
id-PICH-ParametersItem-CTCH-SetupRqstTDD							ProtocolIE-ID ::= 167
id-PRACH-ParametersItem-CTCH-SetupRqstTDD							ProtocolIE-ID ::= 20
id-CCTrCH-InformationItem-RL-FailureInd								ProtocolIE-ID ::= 46
id-CCTrCH-InformationItem-RL-RestoreInd								ProtocolIE-ID ::= 47
id-CauseLevel-SyncAdjustmntFailureTDD								ProtocolIE-ID ::= 420
id-CellAdjustmentInfo-SyncAdjustmntRqstTDD							ProtocolIE-ID ::= 421
id-CellAdjustmentInfoItem-SyncAdjustmentRqstTDD						ProtocolIE-ID ::= 494
id-CellSyncBurstInfoList-CellSyncReconfRqstTDD						ProtocolIE-ID ::= 482
id-CellSyncBurstTransInit-CellSyncInitiationRqstTDD					ProtocolIE-ID ::= 422
id-CellSyncBurstMeasureInit-CellSyncInitiationRqstTDD				ProtocolIE-ID ::= 423
id-CellSyncBurstTransReconfiguration-CellSyncReconfRqstTDD			ProtocolIE-ID ::= 424
id-CellSyncBurstMeasReconfiguration-CellSyncReconfRqstTDD			ProtocolIE-ID ::= 425
id-CellSyncBurstTransInfoList-CellSyncReconfRqstTDD					ProtocolIE-ID ::= 426
id-CellSyncBurstMeasInfoList-CellSyncReconfRqstTDD					ProtocolIE-ID ::= 427
id-CellSyncBurstTransReconfInfo-CellSyncReconfRqstTDD				ProtocolIE-ID ::= 428
id-CellSyncInfo-CellSyncReprtTDD									ProtocolIE-ID ::= 429
id-CSBTransmissionID												ProtocolIE-ID ::= 430
id-CSBMeasurementID													ProtocolIE-ID ::= 431
id-IntStdPhCellSyncInfoItem-CellSyncReprtTDD						ProtocolIE-ID ::= 432
id-NCyclesPerSFNperiod 												ProtocolIE-ID ::= 433
id-NRepetitionsPerCyclePeriod										ProtocolIE-ID ::= 434
id-SyncFrameNumber													ProtocolIE-ID ::= 437
id-SynchronisationReportType										ProtocolIE-ID ::= 438
id-SynchronisationReportCharacteristics								ProtocolIE-ID ::= 439
id-Unsuccessful-cell-InformationRespItem-SyncAdjustmntFailureTDD	ProtocolIE-ID ::= 440
id-LateEntranceCellSyncInfoItem-CellSyncReprtTDD					ProtocolIE-ID ::= 119
id-ReferenceClockAvailability										ProtocolIE-ID ::= 435
id-ReferenceSFNoffset												ProtocolIE-ID ::= 436
id-InformationExchangeID											ProtocolIE-ID ::= 444
id-InformationExchangeObjectType-InfEx-Rqst							ProtocolIE-ID ::= 445
id-InformationType													ProtocolIE-ID ::= 446
id-InformationReportCharacteristics									ProtocolIE-ID ::= 447
id-InformationExchangeObjectType-InfEx-Rsp							ProtocolIE-ID ::= 448
id-InformationExchangeObjectType-InfEx-Rprt							ProtocolIE-ID ::= 449
id-IPDLParameter-Information-Cell-ReconfRqstFDD						ProtocolIE-ID ::= 451
id-IPDLParameter-Information-Cell-SetupRqstFDD						ProtocolIE-ID ::= 452
id-IPDLParameter-Information-Cell-ReconfRqstTDD						ProtocolIE-ID ::= 453
id-IPDLParameter-Information-Cell-SetupRqstTDD						ProtocolIE-ID ::= 454
id-DL-DPCH-LCR-Information-RL-SetupRqstTDD							ProtocolIE-ID ::= 74
id-DwPCH-LCR-Information											ProtocolIE-ID ::= 78
id-DwPCH-LCR-InformationList-AuditRsp                   			ProtocolIE-ID ::= 90
id-DwPCH-LCR-Information-Cell-SetupRqstTDD                   		ProtocolIE-ID ::= 97
id-DwPCH-LCR-Information-Cell-ReconfRqstTDD							ProtocolIE-ID ::= 99
id-DwPCH-LCR-Information-ResourceStatusInd							ProtocolIE-ID ::= 101
id-maxFACH-Power-LCR-CTCH-SetupRqstTDD                   			ProtocolIE-ID ::= 154
id-maxFACH-Power-LCR-CTCH-ReconfRqstTDD                   			ProtocolIE-ID ::= 174
id-FPACH-LCR-Information											ProtocolIE-ID ::= 290
id-FPACH-LCR-Information-AuditRsp                   				ProtocolIE-ID ::= 292
id-FPACH-LCR-InformationList-AuditRsp                   			ProtocolIE-ID ::= 22
id-FPACH-LCR-InformationList-ResourceStatusInd                   	ProtocolIE-ID ::= 311
id-FPACH-LCR-Parameters-CTCH-SetupRqstTDD                   		ProtocolIE-ID ::= 312
id-FPACH-LCR-Parameters-CTCH-ReconfRqstTDD                   		ProtocolIE-ID ::= 314
id-PCCPCH-LCR-Information-Cell-SetupRqstTDD                   		ProtocolIE-ID ::= 456
id-PCH-Power-LCR-CTCH-SetupRqstTDD									ProtocolIE-ID ::= 457
id-PCH-Power-LCR-CTCH-ReconfRqstTDD									ProtocolIE-ID ::= 458
id-PICH-LCR-Parameters-CTCH-SetupRqstTDD                   			ProtocolIE-ID ::= 459
id-PRACH-LCR-ParametersList-CTCH-SetupRqstTDD                  		ProtocolIE-ID ::= 461
id-RL-InformationResponse-LCR-RL-SetupRspTDD	                   	ProtocolIE-ID ::= 463
id-Secondary-CCPCH-LCR-parameterList-CTCH-SetupRqstTDD              ProtocolIE-ID ::= 465
id-TimeSlot															ProtocolIE-ID ::= 495
id-TimeSlotConfigurationList-LCR-Cell-ReconfRqstTDD                 ProtocolIE-ID ::= 466
id-TimeSlotConfigurationList-LCR-Cell-SetupRqstTDD                  ProtocolIE-ID ::= 467
id-TimeslotISCP-LCR-InfoList-RL-SetupRqstTDD                   		ProtocolIE-ID ::= 468
id-TimeSlotLCR-CM-Rqst                   							ProtocolIE-ID ::= 469
id-UL-DPCH-LCR-Information-RL-SetupRqstTDD                   		ProtocolIE-ID ::= 470
id-DL-DPCH-InformationItem-LCR-RL-AdditionRqstTDD					ProtocolIE-ID ::= 472
id-UL-DPCH-InformationItem-LCR-RL-AdditionRqstTDD					ProtocolIE-ID ::= 473
id-TimeslotISCP-InformationList-LCR-RL-AdditionRqstTDD				ProtocolIE-ID ::= 474
id-DL-DPCH-LCR-InformationAddList-RL-ReconfPrepTDD					ProtocolIE-ID ::= 475
id-DL-DPCH-LCR-InformationModify-AddList-RL-ReconfPrepTDD			ProtocolIE-ID ::= 477
id-DL-Timeslot-LCR-InformationModify-ModifyList-RL-ReconfPrepTDD	ProtocolIE-ID ::= 479
id-TimeslotISCPInfoList-LCR-DL-PC-RqstTDD							ProtocolIE-ID ::= 480
id-UL-DPCH-LCR-InformationAddListIE-RL-ReconfPrepTDD				ProtocolIE-ID ::= 481
id-UL-DPCH-LCR-InformationModify-AddList							ProtocolIE-ID ::= 483
id-UL-TimeslotLCR-Information-RL-ReconfPrepTDD						ProtocolIE-ID ::= 485
id-UL-SIRTarget														ProtocolIE-ID ::= 510
id-PDSCH-AddInformation-LCR-PSCH-ReconfRqst							ProtocolIE-ID ::= 486
id-PDSCH-AddInformation-LCR-AddListIE-PSCH-ReconfRqst				ProtocolIE-ID ::= 487
id-PDSCH-Information-Cell-SetupRqstFDD								ProtocolIE-ID ::=  26
id-PDSCH-Information-Cell-ReconfRqstFDD								ProtocolIE-ID ::=  27
id-PDSCH-ModifyInformation-LCR-PSCH-ReconfRqst						ProtocolIE-ID ::= 488
id-PDSCH-ModifyInformation-LCR-ModifyListIE-PSCH-ReconfRqst			ProtocolIE-ID ::= 489
id-PUSCH-AddInformation-LCR-PSCH-ReconfRqst							ProtocolIE-ID ::= 490
id-PUSCH-AddInformation-LCR-AddListIE-PSCH-ReconfRqst				ProtocolIE-ID ::= 491
id-PUSCH-ModifyInformation-LCR-PSCH-ReconfRqst						ProtocolIE-ID ::= 492
id-PUSCH-ModifyInformation-LCR-ModifyListIE-PSCH-ReconfRqst			ProtocolIE-ID ::= 493
id-timeslotInfo-CellSyncInitiationRqstTDD							ProtocolIE-ID ::= 496
id-SyncReportType-CellSyncReprtTDD									ProtocolIE-ID ::= 497
id-Power-Local-Cell-Group-InformationItem-AuditRsp					ProtocolIE-ID ::= 498
id-Power-Local-Cell-Group-InformationItem-ResourceStatusInd			ProtocolIE-ID ::= 499
id-Power-Local-Cell-Group-InformationItem2-ResourceStatusInd		ProtocolIE-ID ::= 500
id-Power-Local-Cell-Group-InformationList-AuditRsp					ProtocolIE-ID ::= 501
id-Power-Local-Cell-Group-InformationList-ResourceStatusInd			ProtocolIE-ID ::= 502
id-Power-Local-Cell-Group-InformationList2-ResourceStatusInd		ProtocolIE-ID ::= 503
id-Power-Local-Cell-Group-ID										ProtocolIE-ID ::= 504
id-PUSCH-Info-DM-Rqst												ProtocolIE-ID ::= 505
id-PUSCH-Info-DM-Rsp												ProtocolIE-ID ::= 506
id-PUSCH-Info-DM-Rprt												ProtocolIE-ID ::= 507
id-InitDL-Power														ProtocolIE-ID ::= 509
id-cellSyncBurstRepetitionPeriod									ProtocolIE-ID ::= 511
id-ReportCharacteristicsType-OnModification							ProtocolIE-ID ::= 512
id-SFNSFNMeasurementValueInformation								ProtocolIE-ID ::= 513
id-SFNSFNMeasurementThresholdInformation							ProtocolIE-ID ::= 514
id-TUTRANGPSMeasurementValueInformation								ProtocolIE-ID ::= 515
id-TUTRANGPSMeasurementThresholdInformation							ProtocolIE-ID ::= 516
id-Rx-Timing-Deviation-Value-LCR									ProtocolIE-ID ::= 520
id-RL-InformationResponse-LCR-RL-AdditionRspTDD						ProtocolIE-ID ::= 51
id-DL-PowerBalancing-Information									ProtocolIE-ID ::= 28
id-DL-PowerBalancing-ActivationIndicator							ProtocolIE-ID ::= 29
id-DL-PowerBalancing-UpdatedIndicator								ProtocolIE-ID ::= 30
id-CCTrCH-Initial-DL-Power-RL-SetupRqstTDD							ProtocolIE-ID ::= 517
id-CCTrCH-Initial-DL-Power-RL-AdditionRqstTDD						ProtocolIE-ID ::= 518
id-CCTrCH-Initial-DL-Power-RL-ReconfPrepTDD							ProtocolIE-ID ::= 519
id-IPDLParameter-Information-LCR-Cell-SetupRqstTDD					ProtocolIE-ID ::= 41
id-IPDLParameter-Information-LCR-Cell-ReconfRqstTDD 				ProtocolIE-ID ::= 42
id-HS-PDSCH-HS-SCCH-MaxPower-PSCH-ReconfRqst						ProtocolIE-ID ::= 522
id-HS-PDSCH-HS-SCCH-ScramblingCode-PSCH-ReconfRqst					ProtocolIE-ID ::= 523
id-HS-PDSCH-FDD-Code-Information-PSCH-ReconfRqst					ProtocolIE-ID ::= 524
id-HS-SCCH-FDD-Code-Information-PSCH-ReconfRqst						ProtocolIE-ID ::= 525
id-HS-PDSCH-TDD-Information-PSCH-ReconfRqst							ProtocolIE-ID ::= 526
id-Add-To-HS-SCCH-Resource-Pool-PSCH-ReconfRqst						ProtocolIE-ID ::= 527
id-Modify-HS-SCCH-Resource-Pool-PSCH-ReconfRqst						ProtocolIE-ID ::= 528
id-Delete-From-HS-SCCH-Resource-Pool-PSCH-ReconfRqst				ProtocolIE-ID ::= 529
id-bindingID														ProtocolIE-ID ::= 102
id-RL-Specific-DCH-Info												ProtocolIE-ID ::= 103
id-transportlayeraddress 											ProtocolIE-ID ::= 104
id-DelayedActivation 												ProtocolIE-ID ::= 231
id-DelayedActivationList-RL-ActivationCmdFDD						ProtocolIE-ID ::= 232
id-DelayedActivationInformation-RL-ActivationCmdFDD					ProtocolIE-ID ::= 233
id-DelayedActivationList-RL-ActivationCmdTDD						ProtocolIE-ID ::= 234
id-DelayedActivationInformation-RL-ActivationCmdTDD					ProtocolIE-ID ::= 235
id-neighbouringTDDCellMeasurementInformationLCR						ProtocolIE-ID ::= 58
id-SYNCDlCodeId-TransInitLCR-CellSyncInitiationRqstTDD				ProtocolIE-ID ::= 543
id-SYNCDlCodeId-MeasureInitLCR-CellSyncInitiationRqstTDD			ProtocolIE-ID ::= 544
id-SYNCDlCodeIdTransReconfInfoLCR-CellSyncReconfRqstTDD				ProtocolIE-ID ::= 545
id-SYNCDlCodeIdMeasReconfigurationLCR-CellSyncReconfRqstTDD			ProtocolIE-ID ::= 546
id-SYNCDlCodeIdMeasInfoList-CellSyncReconfRqstTDD					ProtocolIE-ID ::= 547
id-SyncDLCodeIdsMeasInfoList-CellSyncReprtTDD						ProtocolIE-ID ::= 548
id-SyncDLCodeIdThreInfoLCR											ProtocolIE-ID ::= 549
id-NSubCyclesPerCyclePeriod-CellSyncReconfRqstTDD					ProtocolIE-ID ::= 550
id-DwPCH-Power														ProtocolIE-ID ::= 551
id-AccumulatedClockupdate-CellSyncReprtTDD							ProtocolIE-ID ::= 552
id-Angle-Of-Arrival-Value-LCR										ProtocolIE-ID ::= 521
id-HSDSCH-FDD-Information											ProtocolIE-ID ::= 530
id-HSDSCH-FDD-Information-Response									ProtocolIE-ID ::= 531
id-HSDSCH-FDD-Information-to-Add									ProtocolIE-ID ::= 532
id-HSDSCH-FDD-Information-to-Delete									ProtocolIE-ID ::= 533
id-HSDSCH-Information-to-Modify										ProtocolIE-ID ::= 534
id-HSDSCH-RNTI														ProtocolIE-ID ::= 535
id-HSDSCH-TDD-Information											ProtocolIE-ID ::= 536
id-HSDSCH-TDD-Information-Response									ProtocolIE-ID ::= 537
id-HSDSCH-TDD-Information-Response-LCR								ProtocolIE-ID ::= 538
id-HSDSCH-TDD-Information-to-Add									ProtocolIE-ID ::= 539
id-HSDSCH-TDD-Information-to-Delete									ProtocolIE-ID ::= 540
id-HSPDSCH-RL-ID													ProtocolIE-ID ::= 541
id-PrimCCPCH-RSCP-DL-PC-RqstTDD										ProtocolIE-ID ::= 542
id-Qth-Parameter													ProtocolIE-ID ::= 64
id-PDSCH-RL-ID														ProtocolIE-ID ::= 66
id-HSDSCH-RearrangeList-Bearer-RearrangeInd							ProtocolIE-ID ::= 553
id-UL-Synchronisation-Parameters-LCR								ProtocolIE-ID ::= 554
id-HSDSCH-FDD-Update-Information									ProtocolIE-ID ::= 555
id-HSDSCH-TDD-Update-Information									ProtocolIE-ID ::= 556
id-DL-DPCH-TimeSlotFormat-LCR-ModifyItem-RL-ReconfPrepTDD          	ProtocolIE-ID ::= 558
id-UL-DPCH-TimeSlotFormat-LCR-ModifyItem-RL-ReconfPrepTDD           ProtocolIE-ID ::= 559

END

-- **************************************************************
--
-- Container definitions
--
-- **************************************************************

NBAP-Containers {
itu-t (0) identified-organization (4) etsi (0) mobileDomain (0) 
umts-Access (20) modules (3) nbap (2) version1 (1) nbap-Containers (5) }

DEFINITIONS AUTOMATIC TAGS ::= 

BEGIN

-- **************************************************************
--
-- IE parameter types from other modules.
--
-- **************************************************************

IMPORTS
	maxProtocolExtensions,
	maxPrivateIEs,
	maxProtocolIEs,
	Criticality,
	Presence,
	PrivateIE-ID,
	ProtocolIE-ID
FROM NBAP-CommonDataTypes;

-- **************************************************************
--
-- Class Definition for Protocol IEs
--
-- **************************************************************

NBAP-PROTOCOL-IES ::= CLASS {
	&id		ProtocolIE-ID 			UNIQUE,
	&criticality	Criticality,
	&Value,
	&presence	Presence
}
WITH SYNTAX {
	ID		&id
	CRITICALITY	&criticality
	TYPE		&Value
	PRESENCE	&presence
}

-- **************************************************************
--
-- Class Definition for Protocol IEs
--
-- **************************************************************

NBAP-PROTOCOL-IES-PAIR ::= CLASS {
	&id			ProtocolIE-ID 			UNIQUE,
	&firstCriticality	Criticality,
	&FirstValue,
	&secondCriticality	Criticality,
	&SecondValue,
	&presence		Presence
}
WITH SYNTAX {
	ID			&id
	FIRST CRITICALITY	&firstCriticality
	FIRST TYPE		&FirstValue
	SECOND CRITICALITY 	&secondCriticality
	SECOND TYPE		&SecondValue
	PRESENCE		&presence
}

-- **************************************************************
--
-- Class Definition for Protocol Extensions
--
-- **************************************************************

NBAP-PROTOCOL-EXTENSION ::= CLASS {
	&id		ProtocolIE-ID 		UNIQUE,
	&criticality	Criticality,
	&Extension,
	&presence		Presence
}
WITH SYNTAX {
	ID		&id
	CRITICALITY	&criticality
	EXTENSION	&Extension
	PRESENCE	&presence
}

-- **************************************************************
--
-- Class Definition for Private IEs
--
-- **************************************************************

NBAP-PRIVATE-IES ::= CLASS {
	&id		PrivateIE-ID,
	&criticality	Criticality,
	&Value,
	&presence		Presence
}
WITH SYNTAX {
	ID		&id
	CRITICALITY	&criticality
	TYPE	&Value
	PRESENCE	&presence
}

-- **************************************************************
--
-- Container for Protocol IEs
--
-- **************************************************************

ProtocolIE-Container {NBAP-PROTOCOL-IES : IEsSetParam} ::= 
	SEQUENCE (SIZE (0..maxProtocolIEs)) OF
	ProtocolIE-Field {{IEsSetParam}}

ProtocolIE-Single-Container {NBAP-PROTOCOL-IES : IEsSetParam} ::=
	ProtocolIE-Field {{IEsSetParam}}

ProtocolIE-Field {NBAP-PROTOCOL-IES : IEsSetParam} ::= SEQUENCE {
	id		NBAP-PROTOCOL-IES.&id		({IEsSetParam}),
	criticality		NBAP-PROTOCOL-IES.&criticality	({IEsSetParam}{@id}),
	value		NBAP-PROTOCOL-IES.&Value	 ({IEsSetParam}{@id})
}

-- **************************************************************
--
-- Container for Protocol IE Pairs
--
-- **************************************************************

ProtocolIE-ContainerPair {NBAP-PROTOCOL-IES-PAIR : IEsSetParam} ::= 
	SEQUENCE (SIZE (0..maxProtocolIEs)) OF
	ProtocolIE-FieldPair {{IEsSetParam}}

ProtocolIE-FieldPair {NBAP-PROTOCOL-IES-PAIR : IEsSetParam} ::= SEQUENCE {
	id				NBAP-PROTOCOL-IES-PAIR.&id			({IEsSetParam}),
	firstCriticality		NBAP-PROTOCOL-IES-PAIR.&firstCriticality	({IEsSetParam}{@id}),
	firstValue			NBAP-PROTOCOL-IES-PAIR.&FirstValue	({IEsSetParam}{@id}),
	secondCriticality		NBAP-PROTOCOL-IES-PAIR.&secondCriticality	({IEsSetParam}{@id}),
	secondValue			NBAP-PROTOCOL-IES-PAIR.&SecondValue	({IEsSetParam}{@id})
}

-- **************************************************************
--
-- Container Lists for Protocol IE Containers
--
-- **************************************************************

ProtocolIE-ContainerList {INTEGER : lowerBound, INTEGER : upperBound, NBAP-PROTOCOL-IES : IEsSetParam} ::=
	SEQUENCE (SIZE (lowerBound..upperBound)) OF
	ProtocolIE-Container {{IEsSetParam}}

ProtocolIE-ContainerPairList {INTEGER : lowerBound, INTEGER : upperBound, NBAP-PROTOCOL-IES-PAIR : IEsSetParam} ::=
	SEQUENCE (SIZE (lowerBound..upperBound)) OF
	ProtocolIE-ContainerPair {{IEsSetParam}}

-- **************************************************************
--
-- Container for Protocol Extensions
--
-- **************************************************************

ProtocolExtensionContainer {NBAP-PROTOCOL-EXTENSION : ExtensionSetParam} ::= 
	SEQUENCE (SIZE (1..maxProtocolExtensions)) OF
	ProtocolExtensionField {{ExtensionSetParam}}

ProtocolExtensionField {NBAP-PROTOCOL-EXTENSION : ExtensionSetParam} ::= SEQUENCE {
	id		NBAP-PROTOCOL-EXTENSION.&id	({ExtensionSetParam}),
	criticality	NBAP-PROTOCOL-EXTENSION.&criticality	({ExtensionSetParam}{@id}),
	extensionValue	NBAP-PROTOCOL-EXTENSION.&Extension	({ExtensionSetParam}{@id})
}

-- **************************************************************
--
-- Container for Private IEs
--
-- **************************************************************

PrivateIE-Container {NBAP-PRIVATE-IES : IEsSetParam} ::= 
	SEQUENCE (SIZE (1..maxPrivateIEs)) OF
	PrivateIE-Field {{IEsSetParam}}

PrivateIE-Field {NBAP-PRIVATE-IES : IEsSetParam} ::= SEQUENCE {
	id			NBAP-PRIVATE-IES.&id	
	({IEsSetParam}),
	criticality			NBAP-PRIVATE-IES.&criticality
	({IEsSetParam}{@id}),
	value		NBAP-PRIVATE-IES.&Value
	({IEsSetParam}{@id})
}

END
