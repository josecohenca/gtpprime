--S-GW P-GW CDR format  3GPP TS 32.015 V3.6.0 (2001-06)and 3GPP TS 32.015 V3.3.0

--<ARRAY SEQUENCE OF>--

--<ARRAY SET OF>--

CDR3G
DEFINITIONS IMPLICIT TAGS       ::=

BEGIN

-- EXPORTS everything

--IMPORTS       

--CellId, Diagnostics, CallDuration, ManagementExtensions, TimeStamp, MSISDN, LocationAreaCode, MessageReference, RecordingEntity, SMSResult, LevelOfCAMELService, CalledNumber, CallingNumber
--FROM GSM1205-DataTypes{ ccitt (0) identified-organization (4) etsi(0) mobileDomain (0) gsm-Operation-Maintenance (3) moduleId (3) gsm-12-05 (5) informationModel (0) asn1Module (2) 1 }

--AddressString, ISDN-AddressString, IMSI, IMEI, DefaultGPRS-Handling, DefaultSMS-Handling, ServiceKey
--FROM MAP-CommonDataTypes { ccitt identified-organization (4) etsi(0) mobileDomain (0) gsmNetworkId (1) moduleId (3) map-CommonDataTypes (18) version5 (5) }


--ManagementExtension
--FROM Attribute-ASN1Module {joint-iso-ccitt ms(9) smi(3) part2 (2) asn1Module(2) 1}

--
-- Note that the syntax of AE-title to be used is from 
-- CCITT Rec. X.227 / ISO 8650 corrigendum and not "ANY"
--
------------------------------------------------------------------------------
--
--  CALL AND EVENT RECORDS
--
------------------------------------------------------------------------------

GPRSCallEventRecord-3GPP32251V860	::= CHOICE 
{
	ggsnMBMSRecord-3GPP32251V860			[77] GGSNMBMSRecord-3GPP32251V860,
	sGWRecord-3GPP32251V860				[78] SGWRecord-3GPP32251V860,
	pGWRecord-3GPP32251V860				[79] PGWRecord-3GPP32251V860
}
GGSNMBMSRecord-3GPP32251V860	 	::= SET
{
	recordType					[0] RecordType,
	ggsnAddress					[1] GSNAddress,
	chargingID					[2] ChargingID,
	listofDownstreamNodes		[3] SEQUENCE OF GSNAddress,
	accessPointNameNI			[4] AccessPointNameNI OPTIONAL,
	servedPDPAddress			[5] PDPAddress OPTIONAL,
	listOfTrafficVolumes		[6] SEQUENCE OF ChangeOfMBMSCondition OPTIONAL,
	recordOpeningTime			[7] TimeStamp,
	duration					[8] CallDuration,
	causeForRecClosing			[9] CauseForRecClosing,
	diagnostics					[10] Diagnostics OPTIONAL,
	recordSequenceNumber		[11] INTEGER OPTIONAL,
	nodeID						[12] NodeID OPTIONAL,
	recordExtensions			[13] ManagementExtensions OPTIONAL,
	localSequenceNumber			[14] LocalSequenceNumber OPTIONAL,
	mbmsInformation				[15] MBMSInformation OPTIONAL
}

------------------------------------------------------------------------------
--
--  8. 3GPP 32.251 V8.6.0 S-GW CDR for UGW
--  A postfix'-3GPP32251V860' is added to all the special data structures in this CDR.
--  
--
------------------------------------------------------------------------------

SGWRecord-3GPP32251V860 	::= SET
{
	recordType					[0] RecordType,
	networkInitiation			[1] NetworkInitiatedPDPContext OPTIONAL,
	servedIMSI					[3] IMSI,
	s-GWAddress					[4] GSNAddress,
	chargingID					[5] ChargingID,
	servingNodeAddress			[6] SEQUENCE OF GSNAddress  OPTIONAL,
	accessPointNameNI			[7] AccessPointNameNI OPTIONAL,
	pdpPDNType					[8] PDPType OPTIONAL,
	servedPDPPDNAddress	[9] PDPAddress OPTIONAL,
	dynamicAddressFlag			[11] DynamicAddressFlag OPTIONAL,
	listOfTrafficVolumes			[12] SEQUENCE OF ChangeOfCharConditions OPTIONAL,   
	recordOpeningTime			[13] TimeStamp,
	duration					[14] CallDuration,
	causeForRecClosing			[15] CauseForRecClosing,
	diagnostics					[16] Diagnostics OPTIONAL,
	recordSequenceNumber		[17] INTEGER OPTIONAL,
	nodeID						[18] NodeID OPTIONAL,
	recordExtensions				[19] ContentInfo OPTIONAL,
	localSequenceNumber			[20] LocalSequenceNumber OPTIONAL,
	apnSelectionMode			[21] APNSelectionMode OPTIONAL,
	servedMSISDN				[22] MSISDN OPTIONAL,
	chargingCharacteristics		[23] ChargingCharacteristics,
	chChSelectionMode			[24] ChChSelectionMode OPTIONAL,
	iMSsignalingContext			[25] NULL OPTIONAL,
	servingNodePLMNIdentifier	[27] PLMN-Id OPTIONAL,
	servedIMEISV				[29] IMEI OPTIONAL,
	rATType						[30] RATType OPTIONAL,
	mSTimeZone 					[31] MSTimeZone OPTIONAL,
	userLocationInformation		[32] OCTET STRING OPTIONAL,
	cAMELChargingInformation	[33] OCTET STRING OPTIONAL,
	sGWChange					[34] SGWChange OPTIONAL,
	servingNodeType				[35] SEQUENCE OF ServingNodeType OPTIONAL,
	p-GWAddressUsed				[36] GSNAddress OPTIONAL,
	p-GWPLMNIdentifier			[37] PLMN-Id OPTIONAL,
	startTime					[38] TimeStamp OPTIONAL,
	stopTime					[39] TimeStamp OPTIONAL,
	pDNConnectionID				[40] ChargingID OPTIONAL
}

------------------------------------------------------------------------------
--
--  9. 3GPP 32.251 V8.6.0 P-GW CDR for UGW
--  A postfix'-3GPP32251V860' is added to all the special data structures in this CDR.
--  
--
------------------------------------------------------------------------------
PGWRecord-3GPP32251V860 	::= SET
{
	recordType						[0] RecordType,
	servedIMSI						[3] IMSI,
	p-GWAddress						[4] GSNAddress,
	chargingID						[5] ChargingID,
	servingNodeAddress				[6] SEQUENCE OF GSNAddress,
	accessPointNameNI				[7] AccessPointNameNI OPTIONAL,
	pdpPDNType							[8] PDPType OPTIONAL,
	servedPDPPDNAddress		[9] PDPAddress OPTIONAL,
	dynamicAddressFlag				[11] DynamicAddressFlag OPTIONAL,
	listOfTrafficVolumes			[12] SEQUENCE OF ChangeOfCharConditions OPTIONAL,
	recordOpeningTime				[13] TimeStamp,
	duration						[14] CallDuration,
	causeForRecClosing				[15] CauseForRecClosing,
	diagnostics						[16] Diagnostics OPTIONAL,
	recordSequenceNumber			[17] INTEGER OPTIONAL,
	nodeID							[18] NodeID OPTIONAL,
	recordExtensions				[19] ContentInfo OPTIONAL,
	localSequenceNumber				[20] LocalSequenceNumber OPTIONAL,
	apnSelectionMode				[21] APNSelectionMode OPTIONAL,
	servedMSISDN					[22] MSISDN OPTIONAL,
	chargingCharacteristics			[23] ChargingCharacteristics,
	chChSelectionMode				[24] ChChSelectionMode OPTIONAL,
	iMSsignalingContext				[25] NULL OPTIONAL,
	externalChargingID				[26] OCTET STRING OPTIONAL,
	servingNodePLMNIdentifier		[27] PLMN-Id OPTIONAL,
	pSFurnishChargingInformation	[28] PSFurnishChargingInformation OPTIONAL,
	servedIMEISV					[29] IMEI OPTIONAL,
	rATType							[30] RATType OPTIONAL,
	mSTimeZone 						[31] MSTimeZone OPTIONAL,
	userLocationInformation			[32] OCTET STRING OPTIONAL,
	cAMELChargingInformation		[33] OCTET STRING OPTIONAL,
	listOfServiceData				[34] SEQUENCE OF ChangeOfServiceCondition OPTIONAL,
	servingNodeType				[35] SEQUENCE OF  ServingNodeType OPTIONAL,
        servedMNNAI						[36] SubscriptionID OPTIONAL,
	p-GWPLMNIdentifier				[37] PLMN-Id OPTIONAL,
	startTime						[38] TimeStamp OPTIONAL,
	stopTime						[39] TimeStamp OPTIONAL,
	served3gpp2MEID					[40] OCTET STRING OPTIONAL,
	pDNConnectionID					[41] ChargingID OPTIONAL

}

------------------------------------------------------------------------------
--
--  MBMS OBJECT IDENTIFIERS
--
------------------------------------------------------------------------------
MBMSInformation			::= SET
{
	tmgi						[1] TMGI,
	mbmsSessionIdentity			[2] MBMSSessionIdentity OPTIONAL,
	mbmsServiceType				[3] MBMSServiceType,
	mbmsUserServiceType			[4] MBMSUserServiceType,
	mbms2G3GIndicator			[5] MBMS2G3GIndicator OPTIONAL,
	fileRepairSupported			[6] BOOLEAN OPTIONAL,
	rAI							[7] RoutingAreaCode OPTIONAL,
	mbmsServiceArea				[8] MBMSServiceArea OPTIONAL,
	requiredMBMSBearerCaps		[9] RequiredMBMSBearerCapabilities OPTIONAL
}

TMGI		::= OCTET STRING
	--
	-- This  octet string 
	-- is a 1:1 copy of the contents (i.e. starting with octet 4) of the "TMGI" 
	-- information element specified in 3GPP TS 29.060 [75].

MBMSSessionIdentity		::= OCTET STRING (SIZE (1))

	--
	-- This octet string is a 1:1 copy of the contents of the MBMS-Session-Identity
	-- AVP specified in 3GPP TS 29.061 [82]

MBMSServiceType		::= ENUMERATED
{
	multicast		(0),
	broadcast		(1)
}

MBMSUserServiceType		::= ENUMERATED
{
	download		(0),
	streaming		(1)
}

MBMS2G3GIndicator		::= ENUMERATED
{
	for2G				(0),	-- For GERAN access only
	for3G				(1),	-- For UTRAN access only
	for2G-AND-3G		(2)	-- For both UTRAN and GERAN access
}

MBMSServiceArea		::= OCTET STRING
	--
	-- Editor's Note: The structure of this octet string is subject to discussions
	-- in other working groups.

RequiredMBMSBearerCapabilities		::= OCTET STRING (SIZE (3..11))

	--
	-- This  octet string 
	-- is a 1:1 copy of the contents (i.e. starting with octet 5) of the "Quality of 
	-- service Profile" information element specified in 3GPP TS 29.060 [75].

------------------------------------------------------------------------------
--
--  OBJECT IDENTIFIERS
--
------------------------------------------------------------------------------

gsm1205InformationModel  OBJECT IDENTIFIER      ::=
        { ccitt (0) identified-organization (4) etsi (0) mobileDomain (0)
        gsm-Operation-Maintenance (3) gsm-12-05 (5) informationModel (0) }

gsm1205ASN1Module       OBJECT IDENTIFIER       ::= 
        { gsm1205InformationModel asn1Module(2) }

------------------------------------------------------------------------------
--
--  COMMON DATA TYPES
--
------------------------------------------------------------------------------

AccessPointNameNI	::= IA5String (SIZE(1..63))
	--
	-- Network Identifier part of APN in  dot representation.
	-- For example, if the complete APN is 'apn1a.apn1b.apn1c.mnc022.mcc111.gprs'
	-- NI is 'apn1a.apn1b.apn1c' and is presented in this form in the CDR..
	--
        

AccessPointNameOI	::= IA5String (SIZE(1..37))
	--
	-- Operator Identifier part of APN in dot representation.
	-- In the 'apn1a.apn1b.apn1c.mnc022.mcc111.gprs' example, the OI portion is 'mnc022.mcc111.gprs'
	-- and is presented in this form in the CDR.
	--
	
	

APNSelectionMode::= ENUMERATED
{
	--
	-- See Information Elements TS 29.060 [75], TS 29.274 [91] or TS 29.275 [92]
	--
	mSorNetworkProvidedSubscriptionVerified				(0),
	mSProvidedSubscriptionNotVerified					(1),
	networkProvidedSubscriptionNotVerified				(2)
}


CAMELAccessPointNameNI	::= AccessPointNameNI

CAMELAccessPointNameOI	::= AccessPointNameOI

CAMELInformationMM		::= SET 
{
	sCFAddress						[1] SCFAddress OPTIONAL,
	serviceKey						[2]	ServiceKey OPTIONAL,
	defaultTransactionHandling	   [3]	DefaultGPRS-Handling OPTIONAL,
	numberOfDPEncountered  		   [4] NumberOfDPEncountered OPTIONAL,
	levelOfCAMELService			   [5] LevelOfCAMELService OPTIONAL,
	freeFormatData					[6] FreeFormatData OPTIONAL,
	fFDAppendIndicator	     		[7]	FFDAppendIndicator OPTIONAL
}




CAMELInformationPDP	::= SET
{
	sCFAddress						[1] SCFAddress OPTIONAL,
	serviceKey						[2]	ServiceKey OPTIONAL,
	defaultTransactionHandling		[3]	DefaultGPRS-Handling OPTIONAL,
	cAMELAccessPointNameNI			[4] CAMELAccessPointNameNI OPTIONAL,
	cAMELAccessPointNameOI			[5] CAMELAccessPointNameOI OPTIONAL,
	numberOfDPEncountered			[6] NumberOfDPEncountered OPTIONAL,
	levelOfCAMELService				[7] LevelOfCAMELService OPTIONAL,
	freeFormatData					[8]	FreeFormatData OPTIONAL,
	fFDAppendIndicator				[9]	FFDAppendIndicator OPTIONAL
}


CAMELInformationSMS		::= SET 
{
	sCFAddress								[1] SCFAddress OPTIONAL,
	serviceKey								[2]	ServiceKey OPTIONAL,
	defaultSMSHandling						[3]	DefaultSMS-Handling OPTIONAL,
	cAMELCallingPartyNumber					[4] CallingNumber OPTIONAL,
	cAMELDestinationSubscriberNumber		[5] SmsTpDestinationNumber OPTIONAL,
	cAMELSMSCAddress						[6] AddressString OPTIONAL,
	freeFormatData							[7]	FreeFormatData OPTIONAL,
	smsReferenceNumber						[8] CallReferenceNumber	OPTIONAL
}


LevelOfCAMELService		::= BIT STRING
{
	basic						(0),
	callDurationSupervision		(1),
	onlineCharging				(2)
}


CauseForRecClosing	::= INTEGER
{
	--
	-- In PGW-CDR and SGW-CDR the value servingNodeChange is used for partial record
	-- generation due to Serving Node Address list Overflow
	-- In SGSN servingNodeChange indicates the SGSN change
	-- 	
	-- LCS related causes belong to the MAP error causes acc. TS 29.002 [60]
	--
	-- cause codes 0 to 15 are defined 'CauseForTerm' (cause for termination)
	--
	normalRelease					(0),
	abnormalRelease			    	(4),
	cAMELInitCallRelease			(5),
	volumeLimit				    	(16),
	timeLimit						(17),
	servingNodeChange						(18),
	maxChangeCond					(19),
	managementIntervention	    	(20),
	intraSGSNIntersystemChange		(21),
	rATChange						(22),
	mSTimeZoneChange				(23),
	sGSNPLMNIDChange 				(24),
	unauthorizedRequestingNetwork	(52),
	unauthorizedLCSClient			(53),
	positionMethodFailure			(54),
	unknownOrUnreachableLCSClient	(58),
	listofDownstreamNodeChange		(59)
}


ChangeCondition	::= ENUMERATED
{
	qoSChange				       			(0),
	tariffTime				       			(1),
	recordClosure			       			(2),
	failureHandlingContinueOngoing		   	(3),
	failureHandlingRetryandTerminateOngoing (4),
	failureHandlingTerminateOngoing	   		(5),
	cGI-SAICHange							(6),
	rAIChange								(7),
	dT-Establishment						(8),
	dT-Removal								(9)
}


ChangeOfCharCondition   ::= SEQUENCE
        --
        -- used in PDP context record only
        --
{
        qosRequested            [1] QoSInformation OPTIONAL,
        qosNegotiated           [2] QoSInformation OPTIONAL,
        dataVolumeGPRSUplink    [3] DataVolumeGPRS,
        dataVolumeGPRSDownlink  [4] DataVolumeGPRS,
        changeCondition         [5] ChangeCondition,
        changeTime              [6] TimeStamp
}

ChangeOfCharConditions	::= SEQUENCE
{
	--
	-- Used in PDP context record only
	-- failureHandlingContinue field used in eGCDR only
	--
	qosRequested				[1] QoSInformations OPTIONAL,
	qosNegotiated				[2] QoSInformations OPTIONAL,
	dataVolumeGPRSUplink		[3] DataVolumeGPRS OPTIONAL,
	dataVolumeGPRSDownlink		[4] DataVolumeGPRS OPTIONAL,
	changeCondition				[5] ChangeCondition,
	changeTime					[6] TimeStamp,
	failureHandlingContinue		[7] FailureHandlingContinue OPTIONAL,
	userLocationInformation		[8] OCTET STRING OPTIONAL,
	ePCQoSInformation			[9] EPCQoSInformation OPTIONAL

}


ChangeLocation	::= SEQUENCE
{
	--
	-- used in SGSNMMRecord only
	--
	locationAreaCode		[0] LocationAreaCode,
	routingAreaCode			[1] RoutingAreaCode,
	cellId					[2] CellId OPTIONAL,
	changeTime				[3] TimeStamp,
	mCC-MNC					[4] PLMN-Id OPTIONAL
}


ChargingCharacteristics	::= OCTET STRING (SIZE(2))
    --
	--	Bit 0-3: Profile Index
	--	Bit 4-15: For Behavior
	--      
        
        

ChargingCharacteristics-3GPP32015V330 ::= OCTET STRING (SIZE(1))
    --
        --  Descriptions for the bits of the flag set:
        --
        --  Bit 1: H (Hot billing)              := '00000001'B
        --  Bit 2: F (Flat rate)                := '00000010'B
        --  Bit 3: P (Prepaid service)          := '00000100'B
        --  Bit 4: N (Normal billing)           := '00001000'B


ChargingID	::= INTEGER (0..4294967295)
	--
	-- Generated in P-GW, part of IP CAN bearer	
	-- 0..4294967295 is equivalent to 0..2**32-1
	--
	
	
        
ChChSelectionMode		::= ENUMERATED
{
	servingNodeSupplied			(0),	-- For S-GW/P-GW
	subscriptionSpecific		(1),	-- For SGSN only
	aPNSpecific					(2),	-- For SGSN only
	homeDefault					(3),	 -- For SGSN, S-GW and P-GW
	roamingDefault				(4),	-- For SGSN, S-GW and P-GW
	visitingDefault				(5)		-- For SGSN, S-GW and P-GW
}

DataVolumeGPRS	::= INTEGER (-9223372036854775808..9223372036854775807)
	--
	-- The volume of data transferred in octets.
	--
        --


	
DefaultGPRS-Handling ::= ENUMERATED 
{
	continueTransaction (0) ,
	releaseTransaction (1)
}
-- exception handling:
-- reception of values in range 2-31 shall be treated as "continueTransaction"
-- reception of values greater than 31 shall be treated as "releaseTransaction"

DefaultSMS-Handling ::= ENUMERATED 
{
	continueTransaction (0) ,
	releaseTransaction (1)
}
--	exception handling:
--	reception of values in range 2-31 shall be treated as "continueTransaction"
--	reception of values greater than 31 shall be treated as "releaseTransaction"

DynamicAddressFlag	::= BOOLEAN

EPCQoSInformation	::= SEQUENCE
{
	--
	-- See TS 29.212 [88] for more information
	-- 
	qCI	                [1] INTEGER,
	maxRequestedBandwithUL	[2] INTEGER OPTIONAL,
	maxRequestedBandwithDL	[3] INTEGER OPTIONAL,
	guaranteedBitrateUL		[4] INTEGER OPTIONAL,
	guaranteedBitrateDL		[5] INTEGER OPTIONAL,
	aRP						[6] INTEGER OPTIONAL
}

ETSIAddress	::= AddressString
	--
	-- First octet for nature of address, and numbering plan indicator (3 for X.121)
	-- Other octets TBCD
	-- See TS 29.002 [60]
	-- See TS 29.002 [60]
	--


FFDAppendIndicator      ::= BOOLEAN


FreeFormatData	::=	OCTET STRING (SIZE(1..160))
	--
	-- Free formated data as sent in the FurnishChargingInformationGPRS 
	-- see TS 29.078 [66]
	--
GSNAddress	::= IPAddress
GSMQoSInformation       ::=SEQUENCE
{
        reliability                     [0] QoSReliability,
        delay                           [1] QoSDelay,
        precedence                      [2] QoSPrecedence,
        peakThroughput                  [3] QoSPeakThroughput,
        meanThroughput                  [4] QoSMeanThroughput
}
	

IPAddress	::= CHOICE
{
	iPBinaryAddress	 IPBinaryAddress,
	iPTextRepresentedAddress	 IPTextRepresentedAddress
}


IPBinaryAddress ::= CHOICE
{
        iPBinV4Address                  [0] OCTET STRING (SIZE(4)),
        iPBinV6Address                  [1] OCTET STRING (SIZE(16))
}

IPTextRepresentedAddress        ::= CHOICE
{       --
        -- IP address in the familiar "dot" notation
        --
        iPTextV4Address                 [2] IA5String (SIZE(7..15)),
        iPTextV6Address                 [3] IA5String (SIZE(15..45))
}

LocalSequenceNumber ::= INTEGER (0..4294967295)
        --
        -- Sequence number of the record in this node
        -- 0.. 4294967295 is equivalent to 0..2**32-1, unsigned integer in four octets
        --       
        

MSNetworkCapability-3GPP32015V330     ::= OCTET STRING (SIZE(1))

MSNetworkCapability	::= OCTET STRING (SIZE(1..8))
	-- see TS 24.008 [64]
	
NetworkInitiatedPDPContext	::= BOOLEAN
	--
	-- Set to true if PDP context was initiated from network side
	--
NodeID  ::= IA5String (SIZE(1..20))
PDPAddress      ::= CHOICE
{
        iPAddress                               [0] IPAddress,
        eTSIAddress                             [1] ETSIAddress
}
PDPType		::= OCTET STRING (SIZE(2))
	--
	-- OCTET 1: PDP Type Organization
	-- OCTET 2: PDP Type Number
	-- See TS 29.060 [75] for GTP, TS 29.274 [91] for eGTP and TS 29.275 [92] for PMIP
	--
	
PLMN-Id		::= OCTET STRING (SIZE (3))
	--
	--	This is a 1:1 copy from the Routing Area Identity (RAI) IE specified in TS 29.060 [75]
	--  as follows:
	--	OCTET 1 of PLMN-Id = OCTET 2 of RAI  
	--	OCTET 2 of PLMN-Id = OCTET 3 of RAI  
	--	OCTET 3 of PLMN-Id = OCTET 4 of RAI  

QoSDelay                ::= ENUMERATED
{
        --
        -- See Quality of service TS 24.008
        --
        delayClass1                             (1),
        delayClass2                             (2),
        delayClass3                             (3),
        delayClass4                             (4)
}

QoSInformation  ::= CHOICE
{
        gsmQosInformation               [0] GSMQoSInformation,
        --
        -- The "GSMQoSInformation corresponds to the encoding specified in GSM TS 12.15, and shall be used for pre-Release 99 terminals only.  The umtsQosInformation octet string is a 1:1 copy of the contents (i.e. starting with octet 4) of the "Quality of service Profile" information element specified in 3GPP TS 29.060 [22].

        umtsQosInformation              [1] OCTET STRING (SIZE (4..15))
        --
        -- The umtsQosInformation octet string is a 1:1 copy of the contents (i.e. starting with 
        -- octet 3) of the "Quality of service" information element specified in TS 24.008.
}


QoSInformations	::= OCTET STRING (SIZE (4..255))
	--
	-- This  octet string 
	-- is a 1:1 copy of the contents (i.e. starting with octet 5) of the "Bearer Quality of 
	-- Service" information element specified in TS 29.274 [92].



--
-- This  octet string 
-- is a 1:1 copy of the contents (i.e. starting with octet 4) of the "Quality of 
-- service Profile" information element specified in 3GPP TS 29.060 [22].

QoSMeanThroughput       ::= ENUMERATED
{
        --
	-- See Quality of service TS 24.008
	-- MS to network direction
	-- Network to MS direction needs not to be covered since value (0) = "reserved"
	--
	subscribedMeanThroughput	(0), 
        mean100octetPh                  (1),
        mean200octetPh                  (2),
        mean500octetPh                  (3),
        mean1000octetPh                 (4),
        mean2000octetPh                 (5),
        mean5000octetPh                 (6),
        mean10000octetPh                (7),
        mean20000octetPh                (8),
        mean50000octetPh                (9),
        mean100000octetPh               (10),
        mean200000octetPh               (11),
        mean500000octetPh               (12),
        mean1000000octetPh              (13),
        mean2000000octetPh              (14),
        mean5000000octetPh              (15),
        mean10000000octetPh             (16),
        mean20000000octetPh             (17),
        mean50000000octetPh             (18),
        reserved			(30),
	bestEffort			(31)
}
QoSPeakThroughput       ::= ENUMERATED
{
        --
        -- See Quality of service TS 24.008
        --
        unspecified             (0),
        upTo1000octetPs         (1),
        upTo2000octetPs         (2),
        upTo4000octetPs         (3),
        upTo8000octetPs         (4),
        upTo16000octetPs        (5),
        upTo32000octetPs        (6),
        upTo64000octetPs        (7),
        upTo128000octetPs       (8),
        upTo256000octetPs       (9)
}
QoSPrecedence   ::= ENUMERATED
{
        --
        -- See Quality of service TS 24.008
        --
        unspecified                     (0),
        highPriority                    (1),
        normalPriority                  (2),
        lowPriority                     (3)
}
QoSReliability  ::= ENUMERATED
{
        --
        -- See Quality of service TS 24.008
        --
        unspecifiedReliability  (0),
        acknowledgedGTP         (1),
        unackGTPAcknowLLC       (2),
        unackGTPLLCAcknowRLC    (3),
        unackGTPLLCRLC          (4),
        unacknowUnprotectedData (5)
}

RoutingAreaCode	::= OCTET STRING (SIZE(1))
	--
	-- See TS 24.008 [64]	
	--

SCFAddress	::= AddressString
	--
	-- See TS 29.002 [60]
	--

ServiceKey ::= INTEGER (0..2147483647)

NumberOfDPEncountered  ::= INTEGER
--
--

SGSNChange	::= BOOLEAN
	--
	-- present if first record after inter SGSN routing area update
	-- in new SGSN
	--

SystemType  ::= ENUMERATED
{
	unknown				(0),
	iuUTRAN				(1),
	gERAN				(2)
}

--Changes (enhancements) in GSM1205-DataTypes:
RecordType 	::= INTEGER 
{ 

--	Record values 0..17 are CS specific.
--	The contents are defined in TS 32.250 [10]

	moCallRecord		(0),
	mtCallRecord		(1),
	roamingRecord		(2),
	incGatewayRecord	(3),
	outGatewayRecord	(4),
	transitCallRecord	(5),
	moSMSRecord			(6),
	mtSMSRecord			(7),
	moSMSIWRecord		(8),
	mtSMSGWRecord		(9),
	ssActionRecord		(10),
	hlrIntRecord		(11),
	locUpdateHLRRecord	(12),
	locUpdateVLRRecord	(13),
	commonEquipRecord	(14),
	moTraceRecord		(15),	--- used in earlier releases
	mtTraceRecord		(16),	--- used in earlier releases
	termCAMELRecord	    (17),
--
--	Record values 18..22 are GPRS specific.
--	The contents are defined in TS 32.251 [11]
--
	sgsnPDPRecord		(18),
	ggsnPDPRecord		(19),
	sgsnMMRecord		(20),
	sgsnSMORecord		(21),
	sgsnSMTRecord		(22),
-- 
--  Record values 23..25 are CS-LCS specific.
--	The contents are defined in TS 32.250 [10]
--
	mtLCSRecord			(23),
	moLCSRecord			(24),
	niLCSRecord			(25),
-- 
--  Record values 26..28 are GPRS-LCS specific.
--	The contents are defined in TS 32.251 [11]
--
	sgsnMtLCSRecord		(26),
    sgsnMoLCSRecord		(27),
    sgsnNiLCSRecord		(28),
--
--  Record values 30..62 are MMS specific.
--  The contents are defined in TS 32.270 [30]
--
	mMO1SRecord			(30),
	mMO4FRqRecord		(31),
	mMO4FRsRecord		(32),
	mMO4DRecord			(33), 
	mMO1DRecord			(34),
	mMO4RRecord			(35), 
	mMO1RRecord			(36),
	mMOMDRecord			(37), 
	mMR4FRecord			(38), 
	mMR1NRqRecord		(39), 
	mMR1NRsRecord		(40), 
	mMR1RtRecord		(41), 
	mMR1AFRecord		(42), 
	mMR4DRqRecord		(43), 
	mMR4DRsRecord		(44), 
	mMR1RRRecord		(45), 
	mMR4RRqRecord		(46), 
	mMR4RRsRecord		(47), 
	mMRMDRecord			(48),
	mMFRecord			(49),
	mMBx1SRecord		(50),
	mMBx1VRecord		(51),
	mMBx1URecord		(52),
	mMBx1DRecord		(53),
	mM7SRecord			(54),
	mM7DRqRecord		(55),
	mM7DRsRecord		(56),
	mM7CRecord			(57),
	mM7RRecord			(58),
	mM7DRRqRecord		(59),
	mM7DRRsRecord		(60),
	mM7RRqRecord		(61),
	mM7RRsRecord		(62),
--
--  Record values 63..69, 82 are IMS specific.
--  The contents are defined in TS 32.260 [20]
--
	sCSCFRecord			(63),
	pCSCFRecord			(64),
	iCSCFRecord			(65),
	mRFCRecord			(66),
	mGCFRecord			(67),
	bGCFRecord			(68),
	aSRecord			(69),
	egsnPDPRecord		(70),
--
--  Record values 70 is for Flow based Charging
--  The contents are defined in TS 32.251 [11]
--
--
--  Record values 71..75 are LCS specific.
--  The contents are defined in TS 32.271 [31]
--
	lCSGMORecord		(71),
	lCSRGMTRecord		(72),
	lCSHGMTRecord		(73),
	lCSVGMTRecord		(74),
	lCSGNIRecord		(75),
--
--  Record values 76..79 are MBMS specific.
--  The contents are defined in TS 32.251 [11]
--  Record values 76 and 77 are MBMS bearer context specific
--
	sgsnMBMSRecord		(76),
	ggsnMBMSRecord		(77),
--
--  And TS 32.273 [33]
--  Record values 78 and 79 are MBMS service specific
--  and defined in TS 32.273 [33]
--
	sUBBMSCRecord		(78),
	cONTENTBMSCRecord	(79),
--
--  Record Values 80..81 are PoC specific.
--  The contents are defined in TS 32.272 [32]
--
	pPFRecord			(80),
	cPFRecord			(81),
--
--  Record values 82..83 are EPC specific.
--  The contents are defined in TS 32.251 [11] in R8V840
--  
	iBCFRecord			(82),
--
--  Record Value 83 is MMTel specific.
--  The contents are defined in TS 32.275 [35] in R8V860
--
        mMTelRecord			(83),
--  Record values 82..83 are EPC specific.
--  The contents are defined in TS 32.251 [11]
--
	sGWRecord			(84),
	pGWRecord			(85)

}

CalledNumber                    ::= BCDDirectoryNumber (SIZE(10))

CallingNumber                   ::= BCDDirectoryNumber (SIZE(10))
BCDDirectoryNumber		::= OCTET STRING
	-- This type contains the binary coded decimal representation of
	-- a directory number e.g. calling/called/connected/translated number.
	-- The encoding of the octet string is in accordance with the
	-- the elements "Calling party BCD number", "Called party BCD number"
	-- and "Connected number" defined in TS 24.008 [64].
	-- This encoding includes type of number and number plan information
	-- together with a BCD encoded digit string.
	-- It may also contain both a presentation and screening indicator
	-- (octet 3a).
	-- For the avoidance of doubt, this field does not include 
	-- octets 1 and 2, the element name and length, as this would be 
	-- redundant.
	
SMSResult ::= Diagnostics
Diagnostics	::= CHOICE
{
	gsm0408Cause				[0] INTEGER,
	-- See TS 24.008 [64]	
	gsm0902MapErrorValue		[1] INTEGER,
	-- Note: The value to be stored here corresponds to
	-- the local values defined in the MAP-Errors and 
	-- MAP-DialogueInformation modules, for full details
	-- see TS 29.002 [60].
	itu-tQ767Cause				[2] INTEGER,
	-- See ITU-T Q.767 [67]
	networkSpecificCause		[3] ManagementExtension,
	-- To be defined by network operator	
	manufacturerSpecificCause	[4] INTEGER,
	-- To be defined by manufacturer	
	positionMethodFailureCause	[5] PositionMethodFailure-Diagnostic,
	-- see TS 29.002 [60]
	unauthorizedLCSClientCause	[6] UnauthorizedLCSClient-Diagnostic
	-- see TS 29.002 [60]
}
	
-- From other Protocol:
-- 1. GSM 12.05 V7.0.0 (1999-04)
-- 2. CCITT     X.721   Geneva, 1992
-- 3. 3GPP TS 29.002 V3.7.0 (2000-12)  17.7.8 Common data types
MessageReference                ::= OCTET STRING (SIZE(1))

RecordingEntity                 ::= AddressString

CellId	::= OCTET STRING (SIZE(2))
	--
	-- Coded according to TS 24.008 [64]	
	--
LocationAreaCode    ::= OCTET STRING (SIZE(2))
	--
	-- See TS 24.008 [64]
	--
CallDuration 			::= INTEGER
	--
	-- The call duration is counted in seconds. 
	-- For successful calls /sessions / PDP contexts, this is the chargeable duration.
	-- For call attempts this is the call holding time.
	-- 
ManagementExtensions    ::= SET OF ManagementExtension

TimeStamp                                       ::= OCTET STRING (SIZE(9))
        --
        -- The contents of this field are a compact form of the UTCTime format
        -- containing local time plus an offset to universal time. Binary coded
        -- decimal encoding is employed for the digits to reduce the storage and
        -- transmission overhead
        -- e.g. YYMMDDhhmmssShhmm
        -- where
        -- YY   =       Year 00 to 99           BCD encoded
        -- MM   =       Month 01 to 12          BCD encoded
        -- DD   =       Day 01 to 31            BCD encoded
        -- hh   =       hour 00 to 23           BCD encoded
        -- mm   =       minute 00 to 59         BCD encoded
        -- ss   =       second 00 to 59         BCD encoded
        -- S    =       Sign 0 = "+", "-"       ASCII encoded
        -- hh   =       hour 00 to 23           BCD encoded
        -- mm   =       minute 00 to 59         BCD encoded
        --

MSISDN		::= ISDN-AddressString 
	-- 
	-- See TS 23.003 [68]
	--
	

IMEI ::= TBCD-STRING (SIZE (8))
        --      Refers to International Mobile Station Equipment Identity
        --      and Software Version Number (SVN) defined in TS GSM 03.03.
        --      If the SVN is not present the last octet shall contain the
        --      digit 0 and a filler.
        --      If present the SVN shall be included in the last octet.


IMSI ::= TBCD-STRING (SIZE (3..8))
        -- digits of MCC, MNC, MSIN are concatenated in this order.

ManagementExtension ::= SEQUENCE {
                                identifier      OBJECT IDENTIFIER,
                                significance    [1] BOOLEAN DEFAULT FALSE,
                                information     [2] OCTET STRING  }

ContentInfo  ::= SEQUENCE 
{
     extensionType		[0]	INTEGER,
     length			[1]	INTEGER,
     serviceList     		[2] 	SEQUENCE OF ServiceEvent OPTIONAL,
     changeTimeList		[3]     SEQUENCE OF ChangeTimeEvent OPTIONAL,
     recordOpeningTime		[4]	TmoTimeStamp OPTIONAL,
     duration	    		[5]  	TmoCallDuration OPTIONAL,
     transparentVSA    		[6] 	OCTET STRING (SIZE(3..255)) OPTIONAL,
     cdrType               	[7]     BOOLEAN OPTIONAL,
     createTime     		[8]  	TimeStamp  OPTIONAL,    
     chargingType 		[9]  	INTEGER OPTIONAL,
     roaming      		[10]  	BOOLEAN OPTIONAL,
     profile    		[11] 	ProfileID OPTIONAL,
     nsapi      		[12] 	INTEGER OPTIONAL,
     lastActivityTimeUpLink 	[13] 	TimeStamp OPTIONAL,
     lastActivityTimeDownLink 	[14] 	TimeStamp OPTIONAL,
     zoneId 			[15] 	INTEGER OPTIONAL,
     daylightSavingTime 	[16] 	INTEGER OPTIONAL,
     localTimeZone 		[17] 	INTEGER OPTIONAL,
     sgsnChange 		[18]  	BOOLEAN OPTIONAL,
     sessionID 			[19] 	ChargingID OPTIONAL,
     recordOpeningTimeZone      [20] 	INTEGER OPTIONAL,
     saRecordChangeTime 	[21] 	TimeStamp OPTIONAL,
     saRecordChangeTimeZone 	[22]	INTEGER OPTIONAL
}
ServiceEvent ::= SEQUENCE
{
    serviceCode   		[0]  ServiceIdentifier OPTIONAL,
    uplinkVolume		[1]  DataVolumeGPRS OPTIONAL,
    downlinkVolume		[2]  DataVolumeGPRS OPTIONAL,
    usageduration		[3]  INTEGER OPTIONAL,
    url				[5]  OCTET STRING (SIZE(1..120)) OPTIONAL, 
    chargingRuleBaseName	[8]  ChargingRuleBaseName OPTIONAL,
    ratingGroup 		[9]  RatingGroupId OPTIONAL,
    serviceIdentifier		[10] ServiceIdentifier OPTIONAL,
    localSequenceNumber		[11] LocalSequenceNumber OPTIONAL,
    envelopeStartTime		[12] TmoTimeStamp OPTIONAL,
    envelopeEndTime    		[13] TmoTimeStamp OPTIONAL,
    duration			[14] TmoCallDuration OPTIONAL,
    changeTimeTimeZone		[15] INTEGER OPTIONAL
}

ProfileID ::= INTEGER (0..4294967295)


AddressString ::= OCTET STRING (SIZE (1..maxAddressLength))
        -- This type is used to represent a number for addressing
        -- purposes. It is composed of
        --      a)      one octet for nature of address, and numbering plan
        --              indicator.
        --      b)      digits of an address encoded as TBCD-String.

        --      a)      The first octet includes a one bit extension indicator, a
        --              3 bits nature of address indicator and a 4 bits numbering
        --              plan indicator, encoded as follows:

        -- bit 8: 1  (no extension)

        -- bits 765: nature of address indicator
        --      000  unknown
        --      001  international number
        --      010  national significant number
        --      011  network specific number
        --      100  subscriber number
        --      101  reserved
        --      110  abbreviated number
        --      111  reserved for extension

        -- bits 4321: numbering plan indicator
        --      0000  unknown
        --      0001  ISDN/Telephony Numbering Plan (Rec CCITT E.164)
        --      0010  spare
        --      0011  data numbering plan (CCITT Rec X.121)
        --      0100  telex numbering plan (CCITT Rec F.69)
        --      0101  spare
        --      0110  land mobile numbering plan (CCITT Rec E.212)
        --      0111  spare
        --      1000  national numbering plan
        --      1001  private numbering plan
        --      1111  reserved for extension

        --      all other values are reserved.

        --      b)      The following octets representing digits of an address
        --              encoded as a TBCD-STRING.

ISDN-AddressString ::= 
                        AddressString (SIZE (1..maxISDN-AddressLength))
        -- This type is used to represent ISDN numbers.

TBCD-STRING ::= OCTET STRING
        -- This type (Telephony Binary Coded Decimal String) is used to
        -- represent several digits from 0 through 9, *, #, a, b, c, two
        -- digits per octet, each digit encoded 0000 to 1001 (0 to 9),
        -- 1010 (*), 1011 (#), 1100 (a), 1101 (b) or 1110 (c); 1111 used
        -- as filler when there is an odd number of digits.

        -- bits 8765 of octet n encoding digit 2n
        -- bits 4321 of octet n encoding digit 2(n-1) +1

maxAddressLength  INTEGER ::= 20

maxISDN-AddressLength  INTEGER ::= 9

RATType	::= INTEGER (0..255)
	--
	-- Ihis integer is 1:1 copy of the RAT type value as defined in TS 29.060 [75] for GTP, 
	-- TS 29.274 [91] for eGTP and TS 29.275 [92] for PMIP.
	--

PSFurnishChargingInformation  ::= SEQUENCE
{
	pSFreeFormatData	[1] FreeFormatData,
	pSFFDAppendIndicator  	[2] FFDAppendIndicator OPTIONAL
}



MSTimeZone	::= OCTET STRING (SIZE (2))
	--
	-- 1.Octet: Time Zone and 2. Octet: Daylight saving time, see TS 29.060 [75]
	--

ChangeOfServiceCondition	::= SEQUENCE
{
	--
	-- Used for Flow based Charging service data container
	--
	ratingGroup 					[1] RatingGroupId OPTIONAL,
	chargingRuleBaseName			[2] ChargingRuleBaseName OPTIONAL,
	resultCode						[3] ResultCode OPTIONAL,
	localSequenceNumber				[4] LocalSequenceNumber OPTIONAL,
	timeOfFirstUsage				[5] TimeStamp OPTIONAL,
	timeOfLastUsage					[6] TimeStamp OPTIONAL,
	timeUsage 						[7] CallDuration OPTIONAL,
	serviceConditionChange			[8] ServiceConditionChange,
	qoSInformationNeg				[9] EPCQoSInformation OPTIONAL,
	sgsn-Address 					[10] GSNAddress OPTIONAL,
	sGSNPLMNIdentifier 				[11] PLMN-Id OPTIONAL,--协议中定义为SGSNPLMNIdentifier
	datavolumeFBCUplink				[12] DataVolumeGPRS OPTIONAL,
	datavolumeFBCDownlink			[13] DataVolumeGPRS OPTIONAL,
	timeOfReport					[14] TimeStamp,
	rATType							[15] RATType OPTIONAL,
	failureHandlingContinue			[16] FailureHandlingContinue OPTIONAL,
	serviceIdentifier				[17] ServiceIdentifier OPTIONAL,
	pSFurnishChargingInformation	[18] PSFurnishChargingInformation OPTIONAL,
	aFRecordInformation				[19] SEQUENCE OF AFRecordInformation OPTIONAL,
	userLocationInformation			[20] OCTET STRING OPTIONAL,
	eventBasedChargingInformation	[21] EventBasedChargingInformation OPTIONAL,
	timeQuotaMechanism				[22] TimeQuotaMechanism OPTIONAL
}
RatingGroupId ::= INTEGER
	-- 
	-- IP service flow identity (DCCA), range of 4 byte (0...4294967259)
	-- see Rating-Group AVP as used in 3GPP TS 32.299 [40]
	--
ChargingRuleBaseName ::= IA5String (SIZE(1..16))
	-- 
	-- identifier for the group of charging rules
	-- see Charging-Rule-Base-Name AVP as desined in TS 29.212 [88]

ResultCode ::= INTEGER
-- 
	-- charging protocol return value, range of 4 byte (0...4294967259)
	-- see Result-Code AVP as used in 3GPP 29.212 [88]
	--
ServiceConditionChange	::= BIT STRING 
{
	qoSChange 								 (0),	-- bearer modification
	sGSNChange 								 (1), 	-- bearer modification
	sGSNPLMNIDChange 						 (2), 	-- bearer modification
	tariffTimeSwitch 						 (3), 	-- tariff time change
	pDPContextRelease 						 (4), 	-- bearer release
	rATChange 								 (5),	-- bearer modification
	serviceIdledOut 						 (6),	-- IP flow idle out, DCCA QHT expiry
	reserved1 								 (7),	-- old: QCTexpiry is no report event
	configurationChange 					 (8),	-- configuration change
	serviceStop 							 (9), 	-- IP flow termination
	dCCATimeThresholdReached 				(10),	-- DCCA quota reauthorization
	dCCAVolumeThresholdReached 				(11), 	-- DCCA quota reauthorization
	dCCAServiceSpecificUnitThresholdReached	(12), 	-- DCCA quota reauthorization
	dCCATimeExhausted 						(13), 	-- DCCA quota reauthorization
	dCCAVolumeExhausted 					(14), 	-- DCCA quota reauthorization
	dCCAValidityTimeout 					(15), 	-- DCCA quota validity time (QVT expiry)
	reserved2								(16),	-- reserved due to no use case, 
													-- old: return Requested is covered by (17),(18)
	dCCAReauthorisationRequest 				(17), 	-- DCCA quota reauthorization request by OCS
	dCCAContinueOngoingSession 				(18), 	-- DCCA failure handling (CCFH),
													-- continue IP flow
	dCCARetryAndTerminateOngoingSession		(19), 	-- DCCA failure handling (CCFH),
													-- terminate IP flow after DCCA retry
	dCCATerminateOngoingSession 			(20), 	-- DCCA failure handling,
													-- terminate IP flow
	cGI-SAIChange							(21), 	-- bearer modification
	rAIChange								(22), 	-- bearer modification
	dCCAServiceSpecificUnitExhausted		(23), 	-- DCCA quota reauthorization
	recordClosure							(24),	-- PGW-CDR closure
	timeLimit								(25),	-- intermediate recording
	volumeLimit								(26),	-- intermediate recording
	serviceSpecificUnitLimit				(27),	-- intermediate recording
	envelopeClosure 						(28)
} 
-- Trigger and cause values for IP flow level recording are defined for support of independent
-- online and offline charging and also for tight interworking between online and offline charging.
-- Unused bits will always be zero.
-- Some of the values are non-exclusive (e.g. bearer modification reasons).
FailureHandlingContinue  ::= BOOLEAN
	--
-- This parameter is included when the failure handling procedure has been executed and new 
-- containers are opened. This parameter shall be included in the first and subsequent 
-- containers opened after the failure handling execution.
	--
ServiceIdentifier	::= INTEGER (0..4294967295)
	--
	-- The service identifier is used to identify the service or the service component
	-- the service data flow relates to. See Service-Identifier AVP as defined 
	-- in TS 29.212 [88]
	--
	

------------------------------------------------------------------------------
--
--  3Gpp R7 ADDED DATA	
--
------------------------------------------------------------------------------

AFChargingIdentifier ::= OCTET STRING
    --
    -- see AF-Charging-Identifier AVP as defined in TS 29.214[89]
    --

AFRecordInformation	::= SEQUENCE
{
	aFChargingIdentifier		[1] AFChargingIdentifier,
	flows						[2] Flows OPTIONAL
}
ChangeOfMBMSCondition	::= SEQUENCE
{
	--
	-- Used in MBMS record
	--
	qosRequested				[1] QoSInformations OPTIONAL,
	qosNegotiated				[2] QoSInformations OPTIONAL,
	dataVolumeMBMSUplink		[3] DataVolumeMBMS OPTIONAL,
	dataVolumeMBMSDownlink		[4] DataVolumeMBMS,
	changeCondition				[5] ChangeCondition,
	changeTime					[6] TimeStamp,
	failureHandlingContinue		[7] FailureHandlingContinue OPTIONAL
}
CallReferenceNumber ::= OCTET STRING (SIZE (1..8))

DataVolumeMBMS	::= INTEGER (-9223372036854775808..9223372036854775807)
	--
	-- The volume of data transferred in octets.
	--
EventBasedChargingInformation  ::= SEQUENCE
{
	numberOfEvents		[1] INTEGER,
	eventTimeStamps  	[2] SEQUENCE OF TimeStamp OPTIONAL
}

Flows  ::= 	SEQUENCE
	--
	-- See Flows AVP as defined in TS 29.214 [89] 
	--
{
	mediaComponentNumber	[1] INTEGER,
	flowNumber  			[2] SEQUENCE OF INTEGER OPTIONAL
}

PositionMethodFailure-Diagnostic ::= ENUMERATED {
	congestion  (0),
	insufficientResources  (1),
	insufficientMeasurementData  (2),
	inconsistentMeasurementData  (3),
	locationProcedureNotCompleted  (4),
	locationProcedureNotSupportedByTargetMS  (5),
	qoSNotAttainable  (6),
	positionMethodNotAvailableInNetwork	(7),
	positionMethodNotAvailableInLocationArea	(8)
}
--	exception handling:
--	any unrecognized value shall be ignored	


SmsTpDestinationNumber ::= OCTET STRING
	--
	-- This type contains the binary coded decimal representation of
	-- the SMS address field the encoding of the octet string is in 
	-- accordance with the definition of address fields in TS 23.040 [72].
	-- This encoding includes type of number and numbering plan indication
	-- together with the address value range.
	--
TimeQuotaMechanism	::= SEQUENCE
{
	timeQuotaType					[1] TimeQuotaType,
	baseTimeInterval				[2] INTEGER
}

TimeQuotaType	::= ENUMERATED
{
	discreteTimePeriod			(0),
	continousTimePeriod			(1),
	tmoContinousTimePeriod			(100)
}	


UnauthorizedLCSClient-Diagnostic ::= ENUMERATED {
	noAdditionalInformation (0),
	clientNotInMSPrivacyExceptionList (1),
	callToClientNotSetup (2),
	privacyOverrideNotApplicable (3),
	disallowedByLocalRegulatoryRequirements (4)
}
--	exception handling:
--	any unrecognized value shall be ignored


------------------------------------------------------------------------------
--
--  TMO EXPAND
--
------------------------------------------------------------------------------


TmoTimeStamp			::= OCTET STRING (SIZE(10))
	--
	-- The contents of this field are a compact form of the UTCTime format
	-- containing local time plus an offset to universal time. Binary coded
	-- decimal encoding is employed for the digits to reduce the storage and
	-- transmission overhead
	-- e.g. yymmddhhmmsss Suuvv	
	-- where
	-- YY 	= 	Year 00 to 99		BCD encoded
	-- MM 	= 	Month 01 to 12 	BCD encoded
	-- DD	=	Day 01 to 31		BCD encoded
	-- hh	=	hour 00 to 23		BCD encoded
	-- mm	=	minute 00 to 59	BCD encoded
	-- ss	=	second 00 to 59	BCD encoded
	-- s	= 	1/ 10 of a second: 0 to 9 BCD encoded
	-- S	=	Sign 0 = "+", "-"	ASCII encoded
	-- hh	=	hour 00 to 23		BCD encoded
	-- mm	=	minute 00 to 59	BCD encoded   

TmoCallDuration			::= OCTET STRING (SIZE(3..12))
	-- The contents of this field are 2^32 - 1. Variable with one digit after the comma
	-- Value is in seconds with one digit after the comma

ChangeTimeEvent ::= SEQUENCE
{
	changeTime  		[1]  	TmoTimeStamp OPTIONAL,
	changeTimeTimeZone	[2] 	INTEGER OPTIONAL	
}

	
ServingNodeType                ::= ENUMERATED
{
        --
        -- See  S5-091084.doc
        --
        sGSN                            (0),
        pMIPSGW                         (1),
        gTPSGW                          (2),
        ePDG                            (3),
        hSGW                            (4),
        mME                             (5)
}

SGWChange 	::= BOOLEAN
	--
	-- Present if this is first record after S-GW change.
	--
SubscriptionID	::= SET
{
	subscriptionIDType	[0]	SubscriptionIDType,
	subscriptionIDData	[1]	UTF8String
}

SubscriptionIDType	::= ENUMERATED
{
	endUserE164		(0),
	endUserIMSI		(1),
	endUserSIPURI    	(2),
	endUserNAI		(3),
	endUserPrivate   	(4)
}

	
END
