NChargingDataTypes {itu-t (0) identified-organization (4) etsi(0) mobileDomain (0) charging (5) wlanChargingDataTypes (3) asn1Module (0) version1 (0)}  

DEFINITIONS IMPLICIT TAGS	::=

BEGIN

-- EXPORTS everything

IMPORTS	
…

FROM GenericChargingDataTypes {itu-t (0) identified-organization (4) etsi(0) mobileDomain (0) charging (5) genericChargingDataTypes (0) asn1Module (0) version1 (0)}  
;

------------------------------------------------------------------------------
--
--  WLAN RECORDS
--
------------------------------------------------------------------------------

-- …

------------------------------------------------------------------------------
--
--  WLAN DATA TYPES
--
------------------------------------------------------------------------------

-- …
