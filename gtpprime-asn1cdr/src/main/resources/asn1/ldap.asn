-- foo --

    Lightweight-Directory-Access-Protocol-V3 DEFINITIONS
    IMPLICIT TAGS ::= --pragma {packagePrefix: "ldapd.common.ber"}

    BEGIN

        LDAPMessage ::= SEQUENCE {
            messageID       MessageID,
 --           protocolOp      CHOICE {
 --               bindRequest     BindRequest  },
            controls       [0] Controls OPTIONAL
        }

        MessageID ::= INTEGER (0 .. maxInt)

        maxInt INTEGER ::= 2147483647 -- (2^^31 - 1) --

        LDAPOID ::= OCTET STRING

        Controls ::= SEQUENCE OF Control

        Control ::= SEQUENCE {
            controlType     LDAPOID,
            criticality     BOOLEAN DEFAULT FALSE,
            controlValue    OCTET STRING OPTIONAL
        }

    END
